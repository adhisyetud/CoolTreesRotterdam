FME workspace 10_CSV_Processing_Compare_CT_PT.fmw

Parameters:
- DestDataset_SPATIALITE_NATIVE = C:\MSc\Q2_2\Cooling_Rotterdam\Start_3\03_Intermediate_Results\99_All_Year_Energy_Demand\Proposed_Trees\Result_SIM2023\01_Afr_Compare_FT_FPT_All_year_2050.sqlite   # SpatiaLite Database
- SourceDataset_SPATIALITE_NATIVE_4 = C:\MSc\Q2_2\Cooling_Rotterdam\Start_3\03_Intermediate_Results\2Buurt\Compare\2023_2050\PreDiff\01_Afr_2050_All_Year.sqlite   # SpatiaLite Database
- SourceDataset_SPATIALITE_NATIVE = C:\MSc\Q2_2\Cooling_Rotterdam\Start_3\03_Intermediate_Results\2Buurt\Compare\2023_2050\PreDiff\01_Afr_2050_All_Year_FPT.sqlite   # SpatiaLite Database

Readers:
- SPATIALITE_NATIVE_2: SPATIALITE_NATIVE from $(SourceDataset_SPATIALITE_NATIVE)
- SPATIALITE_NATIVE_3: SPATIALITE_NATIVE from $(SourceDataset_SPATIALITE_NATIVE_4)

Writers:
- SPATIALITE_NATIVE_1: SPATIALITE_NATIVE to $(DestDataset_SPATIALITE_NATIVE)

Table1 (reader SPATIALITE_NATIVE_3)
    attributes: gml_id text, gml_parent_id text, citygml_target_uri text, citygml_feature_role text, citygml_feature_role_attr_name text, citygml_feature_role_attr_val text, gml_description text, gml_name text, citygml_creationDate text, citygml_terminationDate text, externalReference{}.externalObject.name text, externalReference{}.externalObject.uri text, externalReference{}.informationSystem text, citygml_generalizes_to{}.xlink_href text, citygml_relative_to_terrain varchar(33), citygml_relative_to_water varchar(38), citygml_appearance{}.xlink_href text, citygml_class text, citygml_class_codeSpace text, citygml_function{} text, citygml_function{}.codeSpace text, citygml_usage{} text, citygml_usage{}.codeSpace text, citygml_year_of_construction text, citygml_year_of_demolition text, citygml_roof_type text, citygml_roof_type_codeSpace text, citygml_measured_height double, citygml_measured_height_units text, citygml_storeys_above_ground varchar(20),
      citygml_storeys_below_ground varchar(20), citygml_storey_heights_above_ground text, citygml_storey_heights_above_ground_units text, citygml_storey_heights_below_ground text, citygml_storey_heights_below_ground_units text, citygml_outer_building_installation{}.xlink_href text, citygml_interior_building_installation{}.xlink_href text, citygml_bounded_by{}.xlink_href text, citygml_level_of_detail{} text, citygml_interior_room{}.xlink_href text, citygml_consists_of_building_part{}.xlink_href text, citygml_address{}.xlink_href text, type text, AANTAL_ADRESSEN text, AANTAL_BOUWLAGEN text, BUURT text, HOOGSTE_BOUWLAAG text, LAAGSTE_BOUWLAAG text, PANDSOORT text, WIJK text, GMLId varchar(39), Footprint area varchar(6), January Heating demand varchar(6), February Heating demand varchar(6), March Heating demand varchar(6), April Heating demand varchar(6), May Heating demand varchar(5), June Heating demand varchar(5), July Heating demand varchar(5), August Heating demand varchar(5),
      September Heating demand varchar(5), October Heating demand varchar(6), November Heating demand varchar(6), December Heating demand varchar(6), January Cooling demand varchar(5), February Cooling demand varchar(5), March Cooling demand varchar(5), April Cooling demand varchar(5), May Cooling demand varchar(6), June Cooling demand varchar(6), July Cooling demand varchar(6), August Cooling demand varchar(6), September Cooling demand varchar(6), October Cooling demand varchar(5), November Cooling demand varchar(5), December Cooling demand varchar(5), Yearly Cooling Demand (kWh/year) varchar(200), Yearly Heating Demand (kWh/year) varchar(200), N_YCD (kWh/m²/year) varchar(200), N_HCD (kWh/m²/year) varchar(200)
    -> AttributeManager_3
AttributeManager_3
    ATTR_TABLE:
      REMOVE citygml_target_uri (buffer)
      REMOVE citygml_feature_role (buffer)
      REMOVE citygml_feature_role_attr_name (buffer)
      REMOVE citygml_feature_role_attr_val (buffer)
      REMOVE gml_description (buffer)
      REMOVE gml_name (buffer)
      REMOVE citygml_creationDate (buffer)
      REMOVE citygml_terminationDate (buffer)
      REMOVE externalReference{}.externalObject.name (buffer)
      REMOVE externalReference{}.externalObject.uri (buffer)
      REMOVE externalReference{}.informationSystem (buffer)
      REMOVE citygml_generalizes_to{}.xlink_href (buffer)
      REMOVE citygml_relative_to_terrain (varchar(33))
      REMOVE citygml_relative_to_water (varchar(38))
      REMOVE citygml_appearance{}.xlink_href (buffer)
      REMOVE citygml_class (buffer)
      REMOVE citygml_class_codeSpace (buffer)
      REMOVE citygml_function{} (buffer)
      REMOVE citygml_function{}.codeSpace (buffer)
      REMOVE citygml_usage{} (buffer)
      REMOVE citygml_usage{}.codeSpace (buffer)
      REMOVE citygml_year_of_construction (buffer)
      REMOVE citygml_year_of_demolition (buffer)
      REMOVE citygml_roof_type (buffer)
      REMOVE citygml_roof_type_codeSpace (buffer)
      REMOVE citygml_measured_height (real64)
      REMOVE citygml_measured_height_units (buffer)
      REMOVE citygml_storeys_above_ground (varchar(20))
      REMOVE citygml_storeys_below_ground (varchar(20))
      REMOVE citygml_storey_heights_above_ground (buffer)
      REMOVE citygml_storey_heights_above_ground_units (buffer)
      REMOVE citygml_storey_heights_below_ground (buffer)
      REMOVE citygml_storey_heights_below_ground_units (buffer)
      REMOVE citygml_outer_building_installation{}.xlink_href (buffer)
      REMOVE citygml_interior_building_installation{}.xlink_href (buffer)
      REMOVE citygml_bounded_by{}.xlink_href (buffer)
      REMOVE citygml_level_of_detail{} (buffer)
      REMOVE citygml_interior_room{}.xlink_href (buffer)
      REMOVE citygml_consists_of_building_part{}.xlink_href (buffer)
      REMOVE citygml_address{}.xlink_href (buffer)
      REMOVE type (buffer)
      REMOVE AANTAL_ADRESSEN (buffer)
      REMOVE AANTAL_BOUWLAGEN (buffer)
      REMOVE BUURT (buffer)
      REMOVE HOOGSTE_BOUWLAAG (buffer)
      REMOVE LAAGSTE_BOUWLAAG (buffer)
      REMOVE PANDSOORT (buffer)
      REMOVE WIJK (buffer)
      REMOVE GMLId (varchar(39))
      REMOVE Footprint area (varchar(6))
      REMOVE January Heating demand (varchar(6))
      REMOVE February Heating demand (varchar(6))
      REMOVE March Heating demand (varchar(6))
      REMOVE April Heating demand (varchar(6))
      REMOVE May Heating demand (varchar(5))
      REMOVE June Heating demand (varchar(5))
      REMOVE July Heating demand (varchar(5))
      REMOVE August Heating demand (varchar(5))
      REMOVE September Heating demand (varchar(5))
      REMOVE October Heating demand (varchar(6))
      REMOVE November Heating demand (varchar(6))
      REMOVE December Heating demand (varchar(6))
      REMOVE January Cooling demand (varchar(5))
      REMOVE February Cooling demand (varchar(5))
      REMOVE March Cooling demand (varchar(5))
      REMOVE April Cooling demand (varchar(5))
      REMOVE May Cooling demand (varchar(6))
      REMOVE June Cooling demand (varchar(6))
      REMOVE July Cooling demand (varchar(6))
      REMOVE August Cooling demand (varchar(6))
      REMOVE September Cooling demand (varchar(6))
      REMOVE October Cooling demand (varchar(5))
      REMOVE November Cooling demand (varchar(5))
      REMOVE December Cooling demand (varchar(5))
      RENAME_SET_VALUE Yearly Cooling Demand (kWh/year) > Yearly Cooling Demand (kWh/year)_CT (varchar(200))
      RENAME_SET_VALUE Yearly Heating Demand (kWh/year) > Yearly Heating Demand (kWh/year)_CT (varchar(200))
      SET_TO Yearly Energy Demand (kWh/year)_CT (varchar(200)) = @add(@Value(Yearly Cooling Demand (kWh/year)_CT),@Value(Yearly Heating Demand (kWh/year)_CT),...)
      RENAME_SET_VALUE N_YCD (kWh/m²/year) > N_YCD (kWh/m²/year)_CT (varchar(200))
      RENAME_SET_VALUE N_HCD (kWh/m²/year) > N_YHD (kWh/m²/year)_CT (varchar(200))
      SET_TO N_YED (kWh/m²/year)_CT (varchar(200)) = @add(@Value(N_YCD (kWh/m²/year)_CT),@Value(N_YHD (kWh/m²/year)_CT),...)
    -> FeatureMerger_3 [REQUESTOR]
Table1 (reader SPATIALITE_NATIVE_2)
    attributes: gml_id text, gml_parent_id text, citygml_target_uri text, citygml_feature_role text, citygml_feature_role_attr_name text, citygml_feature_role_attr_val text, gml_description text, gml_name text, citygml_creationDate text, citygml_terminationDate text, externalReference{}.externalObject.name text, externalReference{}.externalObject.uri text, externalReference{}.informationSystem text, citygml_generalizes_to{}.xlink_href text, citygml_relative_to_terrain varchar(33), citygml_relative_to_water varchar(38), citygml_appearance{}.xlink_href text, citygml_class text, citygml_class_codeSpace text, citygml_function{} text, citygml_function{}.codeSpace text, citygml_usage{} text, citygml_usage{}.codeSpace text, citygml_year_of_construction text, citygml_year_of_demolition text, citygml_roof_type text, citygml_roof_type_codeSpace text, citygml_measured_height double, citygml_measured_height_units text, citygml_storeys_above_ground varchar(20),
      citygml_storeys_below_ground varchar(20), citygml_storey_heights_above_ground text, citygml_storey_heights_above_ground_units text, citygml_storey_heights_below_ground text, citygml_storey_heights_below_ground_units text, citygml_outer_building_installation{}.xlink_href text, citygml_interior_building_installation{}.xlink_href text, citygml_bounded_by{}.xlink_href text, citygml_level_of_detail{} text, citygml_interior_room{}.xlink_href text, citygml_consists_of_building_part{}.xlink_href text, citygml_address{}.xlink_href text, type text, AANTAL_ADRESSEN text, AANTAL_BOUWLAGEN text, BUURT text, HOOGSTE_BOUWLAAG text, LAAGSTE_BOUWLAAG text, PANDSOORT text, WIJK text, GMLId varchar(39), Footprint area varchar(6), January Heating demand varchar(6), February Heating demand varchar(6), March Heating demand varchar(6), April Heating demand varchar(6), May Heating demand varchar(5), June Heating demand varchar(5), July Heating demand varchar(5), August Heating demand varchar(5),
      September Heating demand varchar(5), October Heating demand varchar(6), November Heating demand varchar(6), December Heating demand varchar(6), January Cooling demand varchar(5), February Cooling demand varchar(5), March Cooling demand varchar(5), April Cooling demand varchar(5), May Cooling demand varchar(6), June Cooling demand varchar(6), July Cooling demand varchar(6), August Cooling demand varchar(6), September Cooling demand varchar(6), October Cooling demand varchar(5), November Cooling demand varchar(5), December Cooling demand varchar(5), Yearly Cooling Demand (kWh/year) varchar(200), Yearly Heating Demand (kWh/year) varchar(200), N_YCD (kWh/m²/year) varchar(200), N_HCD (kWh/m²/year) varchar(200)
    -> GeometryRemover
GeometryRemover
    REMOVE_COORDSYS = No
    -> AttributeManager_4
AttributeManager_4
    ATTR_TABLE:
      REMOVE citygml_target_uri (buffer)
      REMOVE citygml_feature_role (buffer)
      REMOVE citygml_feature_role_attr_name (buffer)
      REMOVE citygml_feature_role_attr_val (buffer)
      REMOVE gml_description (buffer)
      REMOVE gml_name (buffer)
      REMOVE citygml_creationDate (buffer)
      REMOVE citygml_terminationDate (buffer)
      REMOVE externalReference{}.externalObject.name (buffer)
      REMOVE externalReference{}.externalObject.uri (buffer)
      REMOVE externalReference{}.informationSystem (buffer)
      REMOVE citygml_generalizes_to{}.xlink_href (buffer)
      REMOVE citygml_relative_to_terrain (varchar(33))
      REMOVE citygml_relative_to_water (varchar(38))
      REMOVE citygml_appearance{}.xlink_href (buffer)
      REMOVE citygml_class (buffer)
      REMOVE citygml_class_codeSpace (buffer)
      REMOVE citygml_function{} (buffer)
      REMOVE citygml_function{}.codeSpace (buffer)
      REMOVE citygml_usage{} (buffer)
      REMOVE citygml_usage{}.codeSpace (buffer)
      REMOVE citygml_year_of_construction (buffer)
      REMOVE citygml_year_of_demolition (buffer)
      REMOVE citygml_roof_type (buffer)
      REMOVE citygml_roof_type_codeSpace (buffer)
      REMOVE citygml_measured_height (real64)
      REMOVE citygml_measured_height_units (buffer)
      REMOVE citygml_storeys_above_ground (varchar(20))
      REMOVE citygml_storeys_below_ground (varchar(20))
      REMOVE citygml_storey_heights_above_ground (buffer)
      REMOVE citygml_storey_heights_above_ground_units (buffer)
      REMOVE citygml_storey_heights_below_ground (buffer)
      REMOVE citygml_storey_heights_below_ground_units (buffer)
      REMOVE citygml_outer_building_installation{}.xlink_href (buffer)
      REMOVE citygml_interior_building_installation{}.xlink_href (buffer)
      REMOVE citygml_bounded_by{}.xlink_href (buffer)
      REMOVE citygml_level_of_detail{} (buffer)
      REMOVE citygml_interior_room{}.xlink_href (buffer)
      REMOVE citygml_consists_of_building_part{}.xlink_href (buffer)
      REMOVE citygml_address{}.xlink_href (buffer)
      REMOVE type (buffer)
      REMOVE AANTAL_ADRESSEN (buffer)
      REMOVE AANTAL_BOUWLAGEN (buffer)
      REMOVE BUURT (buffer)
      REMOVE HOOGSTE_BOUWLAAG (buffer)
      REMOVE LAAGSTE_BOUWLAAG (buffer)
      REMOVE PANDSOORT (buffer)
      REMOVE WIJK (buffer)
      REMOVE GMLId (varchar(39))
      REMOVE Footprint area (varchar(6))
      REMOVE January Heating demand (varchar(6))
      REMOVE February Heating demand (varchar(6))
      REMOVE March Heating demand (varchar(6))
      REMOVE April Heating demand (varchar(6))
      REMOVE May Heating demand (varchar(5))
      REMOVE June Heating demand (varchar(5))
      REMOVE July Heating demand (varchar(5))
      REMOVE August Heating demand (varchar(5))
      REMOVE September Heating demand (varchar(5))
      REMOVE October Heating demand (varchar(6))
      REMOVE November Heating demand (varchar(6))
      REMOVE December Heating demand (varchar(6))
      REMOVE January Cooling demand (varchar(5))
      REMOVE February Cooling demand (varchar(5))
      REMOVE March Cooling demand (varchar(5))
      REMOVE April Cooling demand (varchar(5))
      REMOVE May Cooling demand (varchar(6))
      REMOVE June Cooling demand (varchar(6))
      REMOVE July Cooling demand (varchar(6))
      REMOVE August Cooling demand (varchar(6))
      REMOVE September Cooling demand (varchar(6))
      REMOVE October Cooling demand (varchar(5))
      REMOVE November Cooling demand (varchar(5))
      REMOVE December Cooling demand (varchar(5))
      RENAME_SET_VALUE Yearly Cooling Demand (kWh/year) > Yearly Cooling Demand (kWh/year)_PT (varchar(200))
      RENAME_SET_VALUE Yearly Heating Demand (kWh/year) > Yearly Heating Demand (kWh/year)_PT (varchar(200))
      SET_TO Yearly Energy Demand (kWh/year)_PT (varchar(200)) = @add(@Value(Yearly Cooling Demand (kWh/year)_PT),@Value(Yearly Heating Demand (kWh/year)_PT),...)
      RENAME_SET_VALUE N_YCD (kWh/m²/year) > N_YCD (kWh/m²/year)_PT (varchar(200))
      RENAME_SET_VALUE N_HCD (kWh/m²/year) > N_YHD (kWh/m²/year)_PT (varchar(200))
      SET_TO N_YED (kWh/m²/year)_PT (varchar(200)) = @add(@Value(N_YCD (kWh/m²/year)_PT),@Value(N_YHD (kWh/m²/year)_PT),...)
    -> FeatureMerger_3 [SUPPLIER]
FeatureMerger_3
    ATTR_ACCUM_MODE = Merge Supplier
    ATTR_CONFLICT_RES_LOOKUP = REQUESTOR_IF_CONFLICT
    IGNORE_NULLS = No
    JOIN_KEYS = @Value(gml_id) @Value(gml_id) AUTO
    MERGE_TYPE_VAL = ATTRIBUTES
    PROCESS_DUPS = NO
    REJECT_NULL_MISSING_KEYS = No
    SUPPLIERS_FIRST = No
    ATTR_CONFLICT_RES = Use Requestor
    MERGE_TYPE = Attributes Only
    MERGED -> AttributeManager_5
AttributeManager_5
    ATTR_TABLE:
      SET_TO Diff_N_YED (kWh/m²/year) (real32) = @sub(@Value(N_YED (kWh/m²/year)_PT),@Value(N_YED (kWh/m²/year)_CT))
      SET_TO Diff_N_YCD (kWh/m²/year) (real32) = @sub(@Value(N_YCD (kWh/m²/year)_PT),@Value(N_YCD (kWh/m²/year)_CT))
      SET_TO Diff_N_YHD (kWh/m²/year) (real32) = @sub(@Value(N_YHD (kWh/m²/year)_PT),@Value(N_YHD (kWh/m²/year)_CT))
      SET_TO Diff_YED (real32) = @sub(@Value(Yearly Energy Demand (kWh/year)_PT),@Value(Yearly Energy Demand (kWh/year)_CT))
      SET_TO Diff_YCD (real32) = @sub(@Value(Yearly Cooling Demand (kWh/year)_PT),@Value(Yearly Cooling Demand (kWh/year)_CT))
      SET_TO Diff_YHD (real32) = @sub(@Value(Yearly Heating Demand (kWh/year)_PT),@Value(Yearly Heating Demand (kWh/year)_CT))
    -> Table1 (writer SPATIALITE_NATIVE_1)
Table1 (writer SPATIALITE_NATIVE_1)
    attributes: gml_id text, gml_parent_id text, Diff_N_YED (kWh/m²/year) float, Diff_N_YCD (kWh/m²/year) float, Diff_N_YHD (kWh/m²/year) float, Diff_YED float, Diff_YCD float, Diff_YHD float, Yearly Cooling Demand (kWh/year)_CT varchar(200), Yearly Heating Demand (kWh/year)_CT varchar(200), Yearly Energy Demand (kWh/year)_CT varchar(200), N_YCD (kWh/m²/year)_CT varchar(200), N_YHD (kWh/m²/year)_CT varchar(200), N_YED (kWh/m²/year)_CT varchar(200), Yearly Cooling Demand (kWh/year)_PT varchar(200), Yearly Heating Demand (kWh/year)_PT varchar(200), Yearly Energy Demand (kWh/year)_PT varchar(200), N_YCD (kWh/m²/year)_PT varchar(200), N_YHD (kWh/m²/year)_PT varchar(200), N_YED (kWh/m²/year)_PT varchar(200)
