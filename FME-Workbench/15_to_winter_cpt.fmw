FME workspace 15_to_winter_cpt.fmw

Parameters:
- SourceDataset_SPATIALITE_NATIVE_30 = ""C:\MSc\Q2_2\Cooling_Rotterdam\Start_3\01_Input\BGT_Feijenoord\Afrikaanderwijk_Building.sqlite" "C:\MSc\Q2_2\Cooling_Rotterdam\Start_3\01_Input\BGT_Feijenoord\KVZ_Building.sqlite""   # SpatiaLite Database
- DestDataset_SPATIALITE_NATIVE_5 = C:\MSc\Q2_2\Cooling_Rotterdam\Start_3\03_Intermediate_Results\2Buurt\FPT\S\Round_FPT_Afr_Summer.sqlite   # SpatiaLite Database
- DestDataset_SPATIALITE_NATIVE_6 = C:\MSc\Q2_2\Cooling_Rotterdam\Start_3\03_Intermediate_Results\2Buurt\CPT\W\Round_CPT_Afr_Winter.sqlite   # SpatiaLite Database
- DestDataset_SPATIALITE_NATIVE_7 = C:\MSc\Q2_2\Cooling_Rotterdam\Start_3\03_Intermediate_Results\2Buurt\CPT\W\Round_CPT_Kvz_Winter.sqlite   # SpatiaLite Database
- SourceDataset_SPATIALITE_NATIVE_3 = C:\MSc\Q2_2\Cooling_Rotterdam\Start_3\03_Intermediate_Results\2Buurt\CPT\S\Round_CPT_Kvz_Summer.sqlite   # SpatiaLite Database
- SourceDataset_SPATIALITE_NATIVE = C:\MSc\Q2_2\Cooling_Rotterdam\Start_3\03_Intermediate_Results\2Buurt\CPT\S\Round_CPT_Afr_Summer.sqlite   # SpatiaLite Database

Readers:
- SPATIALITE_NATIVE_7: SPATIALITE_NATIVE from $(SourceDataset_SPATIALITE_NATIVE_30)
- SPATIALITE_NATIVE_1: SPATIALITE_NATIVE from $(SourceDataset_SPATIALITE_NATIVE)
- SPATIALITE_NATIVE_2: SPATIALITE_NATIVE from $(SourceDataset_SPATIALITE_NATIVE_3)

Writers:
- SPATIALITE_NATIVE_24: SPATIALITE_NATIVE to $(DestDataset_SPATIALITE_NATIVE_5)
- SPATIALITE_NATIVE_25: SPATIALITE_NATIVE to $(DestDataset_SPATIALITE_NATIVE_6)
- SPATIALITE_NATIVE_26: SPATIALITE_NATIVE to $(DestDataset_SPATIALITE_NATIVE_7)

building (reader SPATIALITE_NATIVE_7)
    attributes: ogc_fid integer, rowid integer, gml_id text, gml_parent_id text, citygml_target_uri text, citygml_feature_role text, citygml_feature_role_attr_name text, citygml_feature_role_attr_val text, gml_description text, gml_name text, citygml_creationdate text, citygml_terminationdate text, externalreference{}.externalobject.name text, externalreference{}.externalobject.uri text, externalreference{}.informationsystem text, citygml_generalizes_to{}.xlink_href text, citygml_relative_to_terrain text, citygml_relative_to_water text, citygml_appearance{}.xlink_href text, citygml_class text, citygml_class_codespace text, citygml_function{} text, citygml_function{}.codespace text, citygml_usage{} text, citygml_usage{}.codespace text, citygml_year_of_construction text, citygml_year_of_demolition text, citygml_roof_type text, citygml_roof_type_codespace text, citygml_measured_height float,
      citygml_measured_height_units text, citygml_storeys_above_ground text, citygml_storeys_below_ground text, citygml_storey_heights_above_ground text, citygml_storey_heights_above_ground_units text, citygml_storey_heights_below_ground text, citygml_storey_heights_below_ground_units text, citygml_outer_building_installation{}.xlink_href text, citygml_interior_building_installation{}.xlink_href text, citygml_bounded_by{}.xlink_href text, citygml_level_of_detail{} text, citygml_interior_room{}.xlink_href text, citygml_consists_of_building_part{}.xlink_href text, citygml_address{}.xlink_href text, type text, aantal_adressen text, aantal_bouwlagen text, buurt text, hoogste_bouwlaag text, laagste_bouwlaag text, pandsoort text, wijk text, ycd_tree text, yhd_tree text, gmlid text, footprint area text, ycd_proposed_tree text, yhd_proposed_tree text, ycd_diff float, yhd_diff float,
      diff float
    -> Bufferer_17
Bufferer_17
    ANGLE = 22.5
    CAP_STYLE_LOOKUP = CAP_PROJECTING
    CORNER_STYLE_LOOKUP = JOIN_ARC
    MODE = AREA
    OFFSET = 0.2
    OFFSET_UNITS = METERS
    PRECISION = APPROX
    CAP_STYLE = Square
    CORNER_STYLE = Arc
    BUFFERED -> Clipper_17 [CLIPPER]
    BUFFERED -> Clipper_19 [CLIPPER]
round_pt_kvz_summer__table1 (reader SPATIALITE_NATIVE_2)
    attributes: ogc_fid integer, rowid integer, _zmin float, _zmax float, gml_id text
    -> Bufferer_22
Bufferer_22
    ANGLE = 30
    CAP_STYLE_LOOKUP = CAP_ROUND
    CORNER_STYLE_LOOKUP = JOIN_ROUND
    MODE = AREA
    OFFSET = -0.75
    OFFSET_UNITS = METERS
    PRECISION = APPROX
    CAP_STYLE = Round
    CORNER_STYLE = Round
    BUFFERED -> Clipper_19 [CANDIDATE]
Clipper_19
    ADD_NODATA = YES
    BOUNDARY_CASES = INSIDE
    CLEANING_TOLERANCE_LOOKUP = AUTO
    CLIPPED_ATTR = _clipped
    CLIPPERS_FIRST = NO
    GENERATE_LIST = NO
    INVALID_PARTS_HANDLING = REJECT_WHOLE
    MISSING_M_MODE_LOOKUP = LINEAR
    MISSING_Z_MODE_LOOKUP = PLANAR
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    CLEANING_TOLERANCE = Automatic
    MISSING_M_MODE = Linear Interpolation
    MISSING_Z_MODE = Planar Interpolation
    OUTSIDE -> 3DForcer_7
3DForcer_7
    KEEPZVAL = No
    ZVALATTR = @Value(_zmin)
    -> AttributeManager_17
AttributeManager_17
    ATTR_TABLE:
      REMOVE _clipped (char(9))
      REMOVE ogc_fid (int64)
      REMOVE rowid (int64)
    -> Table1 (writer SPATIALITE_NATIVE_26)
Table1 (writer SPATIALITE_NATIVE_26)
    attributes: _zmin float, _zmax float, gml_id text
chosen_proposed_trees (reader SPATIALITE_NATIVE_1)
    attributes: ogc_fid integer, ogc_fid1 integer, ogc_fid0 integer, rowid integer, _zmin float, _zmax float, gml_id text
    -> Bufferer_20
Bufferer_20
    ANGLE = 30
    CAP_STYLE_LOOKUP = CAP_ROUND
    CORNER_STYLE_LOOKUP = JOIN_ROUND
    MODE = AREA
    OFFSET = -0.75
    OFFSET_UNITS = METERS
    PRECISION = APPROX
    CAP_STYLE = Round
    CORNER_STYLE = Round
    BUFFERED -> Clipper_17 [CANDIDATE]
Clipper_17
    ADD_NODATA = YES
    BOUNDARY_CASES = INSIDE
    CLEANING_TOLERANCE_LOOKUP = AUTO
    CLIPPED_ATTR = _clipped
    CLIPPERS_FIRST = NO
    GENERATE_LIST = NO
    INVALID_PARTS_HANDLING = REJECT_WHOLE
    MISSING_M_MODE_LOOKUP = LINEAR
    MISSING_Z_MODE_LOOKUP = PLANAR
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    CLEANING_TOLERANCE = Automatic
    MISSING_M_MODE = Linear Interpolation
    MISSING_Z_MODE = Planar Interpolation
    OUTSIDE -> 3DForcer_5
3DForcer_5
    KEEPZVAL = No
    ZVALATTR = @Value(_zmin)
    -> AttributeManager_15
AttributeManager_15
    ATTR_TABLE:
      REMOVE _clipped (char(9))
      REMOVE ogc_fid (int64)
      REMOVE ogc_fid1 (int64)
      REMOVE ogc_fid0 (int64)
      REMOVE rowid (int64)
    -> Table1 (writer SPATIALITE_NATIVE_25)
Table1 (writer SPATIALITE_NATIVE_25)
    attributes: _zmin float, _zmax float, gml_id text
