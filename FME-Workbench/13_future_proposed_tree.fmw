FME workspace 13_future_proposed_tree.fmw

Parameters:
- SourceDataset_SPATIALITE_NATIVE_30 = ""C:\MSc\Q2_2\Cooling_Rotterdam\Start_3\01_Input\BGT_Feijenoord\Afrikaanderwijk_Building.sqlite" "C:\MSc\Q2_2\Cooling_Rotterdam\Start_3\01_Input\BGT_Feijenoord\KVZ_Building.sqlite""   # SpatiaLite Database
- SourceDataset_SPATIALITE_NATIVE_9 = C:\MSc\Q2_2\Cooling_Rotterdam\Start_3\03_Intermediate_Results\2Buurt\PT\S\Round_PT_Afr_Summer.sqlite   # SpatiaLite Database
- SourceDataset_SPATIALITE_NATIVE_25 = C:\MSc\Q2_2\Cooling_Rotterdam\Start_3\03_Intermediate_Results\2Buurt\PT\S\Round_PT_Kvz_Summer.sqlite   # SpatiaLite Database
- SourceDataset_SPATIALITE_NATIVE_33 = C:\MSc\Q2_2\Cooling_Rotterdam\Start_3\03_Intermediate_Results\2Buurt\PT\W\Round_PT_Afr_Winter.sqlite   # SpatiaLite Database
- SourceDataset_SPATIALITE_NATIVE_35 = C:\MSc\Q2_2\Cooling_Rotterdam\Start_3\03_Intermediate_Results\2Buurt\PT\W\Round_PT_Kvz_Winter.sqlite   # SpatiaLite Database
- DestDataset_SPATIALITE_NATIVE_5 = C:\MSc\Q2_2\Cooling_Rotterdam\Start_3\03_Intermediate_Results\2Buurt\FPT\S\Round_FPT_Afr_Summer.sqlite   # SpatiaLite Database
- DestDataset_SPATIALITE_NATIVE_6 = C:\MSc\Q2_2\Cooling_Rotterdam\Start_3\03_Intermediate_Results\2Buurt\FPT\S\Round_FPT_Afr_Summer.sqlite   # SpatiaLite Database
- DestDataset_SPATIALITE_NATIVE_7 = C:\MSc\Q2_2\Cooling_Rotterdam\Start_3\03_Intermediate_Results\2Buurt\FPT\S\Round_FPT_Kvz_Summer.sqlite   # SpatiaLite Database
- DestDataset_SPATIALITE_NATIVE_8 = C:\MSc\Q2_2\Cooling_Rotterdam\Start_3\03_Intermediate_Results\2Buurt\FPT\W\Round_FPT_Kvz_Winter.sqlite   # SpatiaLite Database
- DestDataset_SPATIALITE_NATIVE_10 = C:\MSc\Q2_2\Cooling_Rotterdam\Start_3\03_Intermediate_Results\2Buurt\FPT\W\Round_FPT_Afr_Winter.sqlite   # SpatiaLite Database

Readers:
- SPATIALITE_NATIVE_7: SPATIALITE_NATIVE from $(SourceDataset_SPATIALITE_NATIVE_30)
- SPATIALITE_NATIVE_20: SPATIALITE_NATIVE from $(SourceDataset_SPATIALITE_NATIVE_9)
- SPATIALITE_NATIVE_21: SPATIALITE_NATIVE from $(SourceDataset_SPATIALITE_NATIVE_25)
- SPATIALITE_NATIVE_22: SPATIALITE_NATIVE from $(SourceDataset_SPATIALITE_NATIVE_33)
- SPATIALITE_NATIVE_23: SPATIALITE_NATIVE from $(SourceDataset_SPATIALITE_NATIVE_35)

Writers:
- SPATIALITE_NATIVE_24: SPATIALITE_NATIVE to $(DestDataset_SPATIALITE_NATIVE_5)
- SPATIALITE_NATIVE_25: SPATIALITE_NATIVE to $(DestDataset_SPATIALITE_NATIVE_6)
- SPATIALITE_NATIVE_26: SPATIALITE_NATIVE to $(DestDataset_SPATIALITE_NATIVE_7)
- SPATIALITE_NATIVE_27: SPATIALITE_NATIVE to $(DestDataset_SPATIALITE_NATIVE_8)
- SPATIALITE_NATIVE_28: SPATIALITE_NATIVE to $(DestDataset_SPATIALITE_NATIVE_10)

building (reader SPATIALITE_NATIVE_7)
    attributes: ogc_fid integer, rowid integer, gml_id text, gml_parent_id text, citygml_target_uri text, citygml_feature_role text, citygml_feature_role_attr_name text, citygml_feature_role_attr_val text, gml_description text, gml_name text, citygml_creationdate text, citygml_terminationdate text, externalreference{}.externalobject.name text, externalreference{}.externalobject.uri text, externalreference{}.informationsystem text, citygml_generalizes_to{}.xlink_href text, citygml_relative_to_terrain text, citygml_relative_to_water text, citygml_appearance{}.xlink_href text, citygml_class text, citygml_class_codespace text, citygml_function{} text, citygml_function{}.codespace text, citygml_usage{} text, citygml_usage{}.codespace text, citygml_year_of_construction text, citygml_year_of_demolition text, citygml_roof_type text, citygml_roof_type_codespace text, citygml_measured_height float,
      citygml_measured_height_units text, citygml_storeys_above_ground text, citygml_storeys_below_ground text, citygml_storey_heights_above_ground text, citygml_storey_heights_above_ground_units text, citygml_storey_heights_below_ground text, citygml_storey_heights_below_ground_units text, citygml_outer_building_installation{}.xlink_href text, citygml_interior_building_installation{}.xlink_href text, citygml_bounded_by{}.xlink_href text, citygml_level_of_detail{} text, citygml_interior_room{}.xlink_href text, citygml_consists_of_building_part{}.xlink_href text, citygml_address{}.xlink_href text, type text, aantal_adressen text, aantal_bouwlagen text, buurt text, hoogste_bouwlaag text, laagste_bouwlaag text, pandsoort text, wijk text, ycd_tree text, yhd_tree text, gmlid text, footprint area text, ycd_proposed_tree text, yhd_proposed_tree text, ycd_diff float, yhd_diff float,
      diff float
    -> Bufferer_17
Bufferer_17
    ANGLE = 22.5
    CAP_STYLE_LOOKUP = CAP_PROJECTING
    CORNER_STYLE_LOOKUP = JOIN_ARC
    MODE = AREA
    OFFSET = 0.2
    OFFSET_UNITS = METERS
    PRECISION = APPROX
    CAP_STYLE = Square
    CORNER_STYLE = Arc
    BUFFERED -> Clipper_17 [CLIPPER]
    BUFFERED -> Clipper_18 [CLIPPER]
    BUFFERED -> Clipper_19 [CLIPPER]
    BUFFERED -> Clipper_20 [CLIPPER]
Table1 (reader SPATIALITE_NATIVE_20)
    attributes: _zmin double, _zmax float, gml_id varchar(200)
    -> Bufferer_20
Bufferer_20
    ANGLE = 30
    CAP_STYLE_LOOKUP = CAP_ROUND
    CORNER_STYLE_LOOKUP = JOIN_ROUND
    MODE = AREA
    OFFSET = 1
    OFFSET_UNITS = METERS
    PRECISION = APPROX
    CAP_STYLE = Round
    CORNER_STYLE = Round
    BUFFERED -> AttributeManager_11
AttributeManager_11
    ATTR_TABLE = SET_TO _zmax (real64) = @add(@Value(_zmax),2.5)
    -> Clipper_17 [CANDIDATE]
Clipper_17
    ADD_NODATA = YES
    BOUNDARY_CASES = INSIDE
    CLEANING_TOLERANCE_LOOKUP = AUTO
    CLIPPED_ATTR = _clipped
    CLIPPERS_FIRST = NO
    GENERATE_LIST = NO
    INVALID_PARTS_HANDLING = REJECT_WHOLE
    MISSING_M_MODE_LOOKUP = LINEAR
    MISSING_Z_MODE_LOOKUP = PLANAR
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    CLEANING_TOLERANCE = Automatic
    MISSING_M_MODE = Linear Interpolation
    MISSING_Z_MODE = Planar Interpolation
    OUTSIDE -> 3DForcer_5
3DForcer_5
    KEEPZVAL = No
    ZVALATTR = @Value(_zmin)
    -> AttributeManager_15
AttributeManager_15
    ATTR_TABLE = REMOVE _clipped (char(9))
    -> Table1 (writer SPATIALITE_NATIVE_25)
Table1 (writer SPATIALITE_NATIVE_25)
    attributes: _zmin double, _zmax float, gml_id varchar(200)
Table1 (reader SPATIALITE_NATIVE_22)
    attributes: _zmin double, _zmax float, gml_id varchar(200)
    -> Bufferer_21
Bufferer_21
    ANGLE = 30
    CAP_STYLE_LOOKUP = CAP_ROUND
    CORNER_STYLE_LOOKUP = JOIN_ROUND
    MODE = AREA
    OFFSET = 0.5
    OFFSET_UNITS = METERS
    PRECISION = APPROX
    CAP_STYLE = Round
    CORNER_STYLE = Round
    BUFFERED -> AttributeManager_12
AttributeManager_12
    ATTR_TABLE = SET_TO _zmax (real64) = @add(@Value(_zmax),2.5)
    -> Clipper_18 [CANDIDATE]
Clipper_18
    ADD_NODATA = YES
    BOUNDARY_CASES = INSIDE
    CLEANING_TOLERANCE_LOOKUP = AUTO
    CLIPPED_ATTR = _clipped
    CLIPPERS_FIRST = NO
    GENERATE_LIST = NO
    INVALID_PARTS_HANDLING = REJECT_WHOLE
    MISSING_M_MODE_LOOKUP = LINEAR
    MISSING_Z_MODE_LOOKUP = PLANAR
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    CLEANING_TOLERANCE = Automatic
    MISSING_M_MODE = Linear Interpolation
    MISSING_Z_MODE = Planar Interpolation
    OUTSIDE -> 3DForcer_6
3DForcer_6
    KEEPZVAL = No
    ZVALATTR = @Value(_zmin)
    -> AttributeManager_16
AttributeManager_16
    ATTR_TABLE = REMOVE _clipped (char(9))
    -> Table1 (writer SPATIALITE_NATIVE_28)
Table1 (writer SPATIALITE_NATIVE_28)
    attributes: _zmin double, _zmax float, gml_id varchar(200)
Table1 (reader SPATIALITE_NATIVE_21)
    attributes: _zmin double, _zmax float, gml_id varchar(200)
    -> Bufferer_22
Bufferer_22
    ANGLE = 30
    CAP_STYLE_LOOKUP = CAP_ROUND
    CORNER_STYLE_LOOKUP = JOIN_ROUND
    MODE = AREA
    OFFSET = 1
    OFFSET_UNITS = METERS
    PRECISION = APPROX
    CAP_STYLE = Round
    CORNER_STYLE = Round
    BUFFERED -> AttributeManager_13
AttributeManager_13
    ATTR_TABLE = SET_TO _zmax (real64) = @add(@Value(_zmax),2.5)
    -> Clipper_19 [CANDIDATE]
Clipper_19
    ADD_NODATA = YES
    BOUNDARY_CASES = INSIDE
    CLEANING_TOLERANCE_LOOKUP = AUTO
    CLIPPED_ATTR = _clipped
    CLIPPERS_FIRST = NO
    GENERATE_LIST = NO
    INVALID_PARTS_HANDLING = REJECT_WHOLE
    MISSING_M_MODE_LOOKUP = LINEAR
    MISSING_Z_MODE_LOOKUP = PLANAR
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    CLEANING_TOLERANCE = Automatic
    MISSING_M_MODE = Linear Interpolation
    MISSING_Z_MODE = Planar Interpolation
    OUTSIDE -> 3DForcer_7
3DForcer_7
    KEEPZVAL = No
    ZVALATTR = @Value(_zmin)
    -> AttributeManager_17
AttributeManager_17
    ATTR_TABLE = REMOVE _clipped (char(9))
    -> Table1 (writer SPATIALITE_NATIVE_26)
Table1 (writer SPATIALITE_NATIVE_26)
    attributes: _zmin double, _zmax float, gml_id varchar(200)
Table1 (reader SPATIALITE_NATIVE_23)
    attributes: _zmin double, _zmax float, gml_id varchar(200)
    -> Bufferer_23
Bufferer_23
    ANGLE = 30
    CAP_STYLE_LOOKUP = CAP_ROUND
    CORNER_STYLE_LOOKUP = JOIN_ROUND
    MODE = AREA
    OFFSET = 0.5
    OFFSET_UNITS = METERS
    PRECISION = APPROX
    CAP_STYLE = Round
    CORNER_STYLE = Round
    BUFFERED -> AttributeManager_14
AttributeManager_14
    ATTR_TABLE = SET_TO _zmax (real64) = @add(@Value(_zmax),2.5)
    -> Clipper_20 [CANDIDATE]
Clipper_20
    ADD_NODATA = YES
    BOUNDARY_CASES = INSIDE
    CLEANING_TOLERANCE_LOOKUP = AUTO
    CLIPPED_ATTR = _clipped
    CLIPPERS_FIRST = NO
    GENERATE_LIST = NO
    INVALID_PARTS_HANDLING = REJECT_WHOLE
    MISSING_M_MODE_LOOKUP = LINEAR
    MISSING_Z_MODE_LOOKUP = PLANAR
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    CLEANING_TOLERANCE = Automatic
    MISSING_M_MODE = Linear Interpolation
    MISSING_Z_MODE = Planar Interpolation
    OUTSIDE -> 3DForcer_8
3DForcer_8
    KEEPZVAL = No
    ZVALATTR = @Value(_zmin)
    -> AttributeManager_18
AttributeManager_18
    ATTR_TABLE = REMOVE _clipped (char(9))
    -> Table1 (writer SPATIALITE_NATIVE_27)
Table1 (writer SPATIALITE_NATIVE_27)
    attributes: _zmin double, _zmax float, gml_id varchar(200)
