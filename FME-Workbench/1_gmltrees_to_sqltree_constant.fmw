FME workspace 1_gmltrees_to_sqltree_constant.fmw

Parameters:
- SourceDataset_SPATIALITE_NATIVE = C:\MSc\Q2_2\Cooling_Rotterdam\Start_3\01_Input\Wijken_Feijenoord.sqlite   # SpatiaLite Database
- SourceDataset_SPATIALITE_NATIVE_8 = C:\MSc\Q2_2\Cooling_Rotterdam\Start_3\01_Input\Buurt_Feijenoord.sqlite   # SpatiaLite Database
- SourceDataset_CITYGML = ""C:\MSc\Q2_2\Cooling_Rotterdam\Start_3\01_Input\citygml_rotterdam\**\01_Katendrecht.gml" "C:\MSc\Q2_2\Cooling_Rotterdam\Start_3\01_Input\citygml_rotterdam\**\02_Kop_Van_Zuid.gml" "C:\MSc\Q2_2\Cooling_Rotterdam\Start_3\01_Input\citygml_rotterdam\**\03_Noordereiland.gml" "C:\MSc\Q2_2\Cooling_Rotterdam\Start_3\01_Input\citygml_rotterdam\**\04_Feijenoord.gml" "C:\MSc\Q2_2\Cooling_Rotterdam\Start_3\01_Input\citygml_rotterdam\**\05_KVZ_Entrepot.gml" "C:\MSc\Q2_2\Cooling_Rotterdam\Start_3\01_Input\citygml_rotterdam\**\06_Afrikaanderwijk.gml" "C:\MSc\Q2_2\Cooling_Rotterdam\Start_3\01_Input\citygml_rotterdam\**\07_Hillesluis.gml" "C:\MSc\Q2_2\Cooling_Rotterdam\Start_3\01_Input\citygml_rotterdam\**\08_Bloemhof.gml" "C:\MSc\Q2_2\Cooling_Rotterdam\Start_3\01_Input\citygml_rotterdam\**\09_Vreewijk_1.gml" "C:\MSc\Q2_2\Cooling_Rotterdam\Start_3\01_Input\citygml_rotterdam\**\10_Vreewijk_2.gml""   # Source CityGML File(s)
- DestDataset_SPATIALITE_NATIVE_25 = C:\MSc\Q2_2\Cooling_Rotterdam\Start_3\03_Intermediate_Results\2Buurt\CT\S\Round_CT_Kvz_Summer.sqlite   # SpatiaLite Database
- DestDataset_SPATIALITE_NATIVE_27 = C:\MSc\Q2_2\Cooling_Rotterdam\Start_3\03_Intermediate_Results\2Buurt\CT\W\Round_CT_Kvz_Winter.sqlite   # SpatiaLite Database
- DestDataset_SPATIALITE_NATIVE = C:\MSc\Q2_2\Cooling_Rotterdam\Start_3\03_Intermediate_Results\2Buurt\CT\S\Round_CT_Afr_Summer.sqlite   # SpatiaLite Database
- DestDataset_CSV2_3 = C:\MSc\Q2_2\Cooling_Rotterdam\Start_3\03_Intermediate_Results   # Destination CSV (Comma Separated Value) Folder
- DestDataset_CSV2 = C:\MSc\Q2_2\Cooling_Rotterdam\Start_3\03_Intermediate_Results   # Destination CSV (Comma Separated Value) Folder
- DestDataset_SPATIALITE_NATIVE_6 = C:\MSc\Q2_2\Cooling_Rotterdam\Start_3\03_Intermediate_Results\2Buurt\CT\W\Round_CT_Afr_Winter.sqlite   # SpatiaLite Database
- SourceDataset_SPATIALITE_NATIVE_30 = ""C:\MSc\Q2_2\Cooling_Rotterdam\Start_3\01_Input\BGT_Feijenoord\Afrikaanderwijk_Building.sqlite" "C:\MSc\Q2_2\Cooling_Rotterdam\Start_3\01_Input\BGT_Feijenoord\KVZ_Building.sqlite""   # SpatiaLite Database

Readers:
- SPATIALITE_NATIVE_1: SPATIALITE_NATIVE from $(SourceDataset_SPATIALITE_NATIVE)
- SPATIALITE_NATIVE_2: SPATIALITE_NATIVE from $(SourceDataset_SPATIALITE_NATIVE_8)
- CITYGML_1: CITYGML from $(SourceDataset_CITYGML)
- SPATIALITE_NATIVE_4: SPATIALITE_NATIVE from $(SourceDataset_SPATIALITE_NATIVE_30)

Writers:
- SPATIALITE_NATIVE_3: SPATIALITE_NATIVE to $(DestDataset_SPATIALITE_NATIVE)
- SPATIALITE_NATIVE_15: SPATIALITE_NATIVE to $(DestDataset_SPATIALITE_NATIVE_25)
- SPATIALITE_NATIVE_16: SPATIALITE_NATIVE to $(DestDataset_SPATIALITE_NATIVE_27)
- CSV2_1: CSV2 to $(DestDataset_CSV2)
- CSV2_2: CSV2 to $(DestDataset_CSV2_3)
- SPATIALITE_NATIVE_5: SPATIALITE_NATIVE to $(DestDataset_SPATIALITE_NATIVE_6)

SolitaryVegetationObject (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_class xml_buffer, citygml_class_codeSpace xml_buffer, citygml_function{} xml_buffer, citygml_function{}.codeSpace xml_buffer, citygml_usage{} xml_buffer, citygml_usage{}.codeSpace xml_buffer, citygml_species xml_buffer, citygml_species_codeSpace xml_buffer, citygml_height xml_real64, citygml_height_units xml_buffer, citygml_trunk_diameter xml_real64, citygml_trunk_diameter_units xml_buffer, citygml_crown_diameter xml_real64, citygml_crown_diameter_units xml_buffer, citygml_level_of_detail{} xml_buffer, Aanlegjaar xml_buffer,
      Beheerobjectomschrijving xml_buffer, Boom_id xml_buffer, Boomsortiment xml_buffer, Boomsortiment_nederlands xml_buffer, Boomstatus xml_buffer, Brondatum xml_buffer, Buurt xml_buffer, Geslacht xml_buffer, Hoogte xml_buffer, Laatste_mutatie xml_buffer, Ontwikkeling xml_buffer, Stamdiameter xml_buffer, Stamlengte xml_buffer, Straat xml_buffer, Thema xml_buffer, Wijk xml_buffer, tree_part xml_buffer
    -> TestFilter_2
TestFilter_2
    DEFAULT_VALUE = <UNFILTERED>
    PASSED_TEST_GROUP_OUTPUT = FIRST
    TEST_LIST = "BOOL_OP,OR,COMPOSITE_TEST,""""""1"""""",TEST_CLAUSE,TEST @Right(@Value(gml_id),1) = K",K
    K -> DuplicateFilter_4
DuplicateFilter_4
    INPUT_ORDERED_CHOICE_LOOKUP = NO
    KEYATTR = gml_id
    INPUT_ORDERED_CHOICE = No
    UNIQUE -> Clipper_4 [CANDIDATE]
    UNIQUE -> UniqueValueLogger
    UNIQUE -> UniqueValueLogger_2
UniqueValueLogger
    VAL = @Value(Geslacht)
    -> Geslacht_Genus (writer CSV2_1)
Geslacht_Genus (writer CSV2_1)
    attributes: _count uint32, _value varchar(200)
UniqueValueLogger_2
    VAL = @Value(Boomsortiment)
    -> Boomsortiment_Species (writer CSV2_2)
Boomsortiment_Species (writer CSV2_2)
    attributes: _count uint32, _value varchar(200)
building (reader SPATIALITE_NATIVE_4)
    attributes: ogc_fid integer, rowid integer, gml_id text, gml_parent_id text, citygml_target_uri text, citygml_feature_role text, citygml_feature_role_attr_name text, citygml_feature_role_attr_val text, gml_description text, gml_name text, citygml_creationdate text, citygml_terminationdate text, externalreference{}.externalobject.name text, externalreference{}.externalobject.uri text, externalreference{}.informationsystem text, citygml_generalizes_to{}.xlink_href text, citygml_relative_to_terrain text, citygml_relative_to_water text, citygml_appearance{}.xlink_href text, citygml_class text, citygml_class_codespace text, citygml_function{} text, citygml_function{}.codespace text, citygml_usage{} text, citygml_usage{}.codespace text, citygml_year_of_construction text, citygml_year_of_demolition text, citygml_roof_type text, citygml_roof_type_codespace text, citygml_measured_height float,
      citygml_measured_height_units text, citygml_storeys_above_ground text, citygml_storeys_below_ground text, citygml_storey_heights_above_ground text, citygml_storey_heights_above_ground_units text, citygml_storey_heights_below_ground text, citygml_storey_heights_below_ground_units text, citygml_outer_building_installation{}.xlink_href text, citygml_interior_building_installation{}.xlink_href text, citygml_bounded_by{}.xlink_href text, citygml_level_of_detail{} text, citygml_interior_room{}.xlink_href text, citygml_consists_of_building_part{}.xlink_href text, citygml_address{}.xlink_href text, type text, aantal_adressen text, aantal_bouwlagen text, buurt text, hoogste_bouwlaag text, laagste_bouwlaag text, pandsoort text, wijk text, ycd_tree text, yhd_tree text, gmlid text, footprint area text, ycd_proposed_tree text, yhd_proposed_tree text, ycd_diff float, yhd_diff float,
      diff float
    -> Bufferer_17
Bufferer_17
    ANGLE = 22.5
    CAP_STYLE_LOOKUP = CAP_PROJECTING
    CORNER_STYLE_LOOKUP = JOIN_ARC
    MODE = AREA
    OFFSET = 0.2
    OFFSET_UNITS = METERS
    PRECISION = APPROX
    CAP_STYLE = Square
    CORNER_STYLE = Arc
    BUFFERED -> Clipper_3 [CLIPPER]
    BUFFERED -> Clipper_2 [CLIPPER]
    BUFFERED -> Clipper_5 [CLIPPER]
    BUFFERED -> Clipper_6 [CLIPPER]
extracted_location (reader SPATIALITE_NATIVE_2)
    attributes: ogc_fid integer, buurtcode text, buurtnaam text, wijkcode text, gemeentecode text, gemeentenaam text, indelingswijzigingwijkenenbuurten integer, water text, meestvoorkomendepostcode text, dekkingspercentage integer, omgevingsadressendichtheid integer, stedelijkheidadressenperkm2 integer, bevolkingsdichtheidinwonersperkm2 integer, aantalinwoners integer, mannen integer, vrouwen integer, percentagepersonen0tot15jaar integer, percentagepersonen15tot25jaar integer, percentagepersonen25tot45jaar integer, percentagepersonen45tot65jaar integer, percentagepersonen65jaarenouder integer, percentageongehuwd integer, percentagegehuwd integer, percentagegescheid integer, percentageverweduwd integer, geboortetotaal integer, geboortesper1000inwoners integer, sterftetotaal integer, sterfterelatief integer, aantalhuishoudens integer,
      percentageeenpersoonshuishoudens integer, percentagehuishoudenszonderkinderen integer, percentagehuishoudensmetkinderen integer, gemiddeldehuishoudsgrootte float, percentagemetherkomstlandnederland integer, percentagemetherkomstlanduiteuropaexclnl integer, percentagemetherkomstlandbuiteneuropa integer, percentagegebinnlmetherkomstlandnederland integer, percgebinnlmetherkomstlandineuropaexnl integer, percgebinnlmetherkomstlandbuiteneuropa integer, percgebbuitennlmetherkomstlndineuropaexnl integer, percgebbuitennlmetherkomstlndbuiteneuropa integer, aantalbedrijvenlandbouwbosbouwvisserij integer, aantalbedrijvennijverheidenergie integer, aantalbedrijvenhandelenhoreca integer, aantalbedrijvenvervoerinformatiecommunicatie integer, aantalbedrijvenfinancieelonroerendgoed integer, aantalbedrijvenzakelijkedienstverlening integer, aantalbedrijvenoverheidonderwijsenzorg integer, aantalbedrijvencultuurrecreatieoverige integer, aantalbedrijfsvestigingen integer, woningvoorraad integer, gemiddeldewoningwaarde integer, percentageeengezinswoning integer, percentagemeergezinswoning integer, percentagebewoond integer, percentagekoopwoningen integer, percentagehuurwoningen integer, perchuurwoningeninbezitwoningcorporaties integer, perchuurwoningeninbezitoverigeverhuurders integer,
      percentagewoningenmeteigendomonbekend integer, percentagebouwjaarklassetot2000 integer, percentagebouwjaarklassevanaf2000 integer, percentageleegstandwoningen integer, gemiddeldgasverbruiktotaal integer, gemiddeldgasverbruikappartement integer, gemiddeldgasverbruiktussenwoning integer, gemiddeldgasverbruikhoekwoning integer, gemiddeldgasverbruik2onder1kapwoning integer, gemiddeldgasverbruikvrijstaandewoning integer, gemiddeldgasverbruikhuurwoning integer, gemiddeldgasverbruikkoopwoning integer, gemiddeldelektriciteitsverbruiktotaal integer, gemiddeldelektriciteitsverbruikappartement integer, gemiddeldelektriciteitsverbruiktussenwoning integer, gemiddeldelektriciteitsverbruikhoekwoning integer, gemelektriciteitsverbruik2onder1kapwoning integer, gemelektriciteitsverbruikvrijstaandewoning integer, gemiddeldelektriciteitsverbruikhuurwoning integer, gemiddeldelektriciteitsverbruikkoopwoning integer, percentagewoningenmetstadsverwarming integer, opleidingsniveaulaag integer, opleidingsniveaumiddelbaar integer, opleidingsniveauhoog integer, nettoarbeidsparticipatie integer, percentagewerknemers integer, percentagezelfstandigen integer, aantalinkomensontvangers integer, gemiddeldinkomenperinkomensontvanger integer, gemiddeldinkomenperinwoner integer,
      percentagepersonenmethooginkomen integer, percentagepersonenmetlaaginkomen integer, percentagehuishoudensmethooginkomen integer, percentagehuishoudensmetlaaginkomen integer, percentagehuishoudensmetlaagsteinkomen integer, percentagehuishoudensonderofrondsociaalminimum integer, aantalpersonenmeteenaouitkeringtotaal integer, aantalpersonenmeteenwwuitkeringtotaal integer, aantalpersonenmeteenalgbijstandsuitkeringtot integer, aantalpersonenmeteenaowuitkeringtotaal integer, gemiddeldgestandaardiseerdinkomenvanhuishoudens float, huishoudenstot110percentvansociaalminimum float, huishoudenstot120percentvansociaalminimum float, mediaanvermogenvanparticulierehuish float, aantaljongerenmetjeugdzorginnatura integer, percentagejongerenmetjeugdzorginnatura float, aantalwmoclienten integer, aantalwmoclientenper1000inwoners integer, personenautostotaal integer, personenautosperhuishouden float, personenautosperkm2 integer, motortweewielerstotaal integer, aantalpersonenautosmetbrandstofbenzine integer, aantalpersonenautosmetoverigebrandstof integer, oppervlaktetotaalinha integer, oppervlaktelandinha integer, oppervlaktewaterinha integer, huisartsenpraktijkgemiddeldeafstandinkm float, huisartsenpraktijkgemiddeldaantalbinnen1km float, huisartsenpraktijkgemiddeldaantalbinnen3km float,
      huisartsenpraktijkgemiddeldaantalbinnen5km float, huisartsenpostgemiddeldeafstandinkm float, apotheekgemiddeldeafstandinkm float, ziekenhuisinclbuitenpolikliniekgemafstinkm float, ziekenhuisinclbuitenpoligemaantalbinnen5km float, ziekenhuisinclbuitenpoligemaantalbinnen10km float, ziekenhuisinclbuitenpoligemaantalbinnen20km float, ziekenhuisexclbuitenpolikliniekgemafstinkm float, ziekenhuisexclbuitenpoligemaantalbinnen5km float, ziekenhuisexclbuitenpoligemaantalbinnen10km float, ziekenhuisexclbuitenpoligemaantalbinnen20km float, grotesupermarktgemiddeldeafstandinkm float, grotesupermarktgemiddeldaantalbinnen1km float, grotesupermarktgemiddeldaantalbinnen3km float, grotesupermarktgemiddeldaantalbinnen5km float, winkelsovdagelijkselevensmgemafstinkm float, winkelsovdagellevensmgemaantalbinnen1km float, winkelsovdagellevensmgemaantalbinnen3km float, winkelsovdagellevensmgemaantalbinnen5km float, warenhuisgemiddeldeafstandinkm float, warenhuisgemiddeldaantalbinnen5km float, warenhuisgemiddeldaantalbinnen10km float, warenhuisgemiddeldaantalbinnen20km float, cafegemiddeldeafstandinkm float, cafegemiddeldaantalbinnen1km float, cafegemiddeldaantalbinnen3km float, cafegemiddeldaantalbinnen5km float, cafetariagemiddeldeafstandinkm float, cafetariagemiddeldaantalbinnen1km float, cafetariagemiddeldaantalbinnen3km float,
      cafetariagemiddeldaantalbinnen5km float, restaurantgemiddeldeafstandinkm float, restaurantgemiddeldaantalbinnen1km float, restaurantgemiddeldaantalbinnen3km float, restaurantgemiddeldaantalbinnen5km float, hotelgemiddeldeafstandinkm float, hotelgemiddeldaantalbinnen5km float, hotelgemiddeldaantalbinnen10km float, hotelgemiddeldaantalbinnen20km float, kinderdagverblijfgemiddeldeafstandinkm float, kinderdagverblijfgemiddeldaantalbinnen1km float, kinderdagverblijfgemiddeldaantalbinnen3km float, kinderdagverblijfgemiddeldaantalbinnen5km float, buitenschoolseopvanggemafstandinkm float, buitenschoolseopvanggemiddeldaantalbinnen1km float, buitenschoolseopvanggemiddeldaantalbinnen3km float, buitenschoolseopvanggemiddeldaantalbinnen5km float, basisonderwijsgemiddeldeafstandinkm float, basisonderwijsgemiddeldaantalbinnen1km float, basisonderwijsgemiddeldaantalbinnen3km float, basisonderwijsgemiddeldaantalbinnen5km float, voortgezetonderwijsgemafstandinkm float, voortgezetonderwijsgemiddeldaantalbinnen3km float, voortgezetonderwijsgemiddeldaantalbinnen5km float, voortgezetonderwijsgemiddeldaantalbinnen10km float, vmbogemiddeldeafstandinkm float, vmbogemiddeldaantalbinnen3km float, vmbogemiddeldaantalbinnen5km float, vmbogemiddeldaantalbinnen10km float, havovwogemiddeldeafstandinkm float,
      havovwogemiddeldaantalbinnen3km float, havovwogemiddeldaantalbinnen5km float, havovwogemiddeldaantalbinnen10km float, brandweerkazernegemiddeldeafstandinkm float, oprithoofdverkeersweggemiddeldeafstandinkm float, treinstationgemiddeldeafstandinkm float, overstapstationgemiddeldeafstandinkm float, zwembadgemiddeldeafstandinkm float, kunstijsbaangemiddeldeafstandinkm float, bibliotheekgemiddeldeafstandinkm float, poppodiumgemiddeldeafstandinkm float, bioscoopgemiddeldeafstandinkm float, bioscoopgemiddeldaantalbinnen5km float, bioscoopgemiddeldaantalbinnen10km float, bioscoopgemiddeldaantalbinnen20km float, saunagemiddeldeafstandinkm float, zonnebankgemiddeldeafstandinkm float, attractieparkgemiddeldeafstandinkm float, attractieparkgemiddeldaantalbinnen10km float, attractieparkgemiddeldaantalbinnen20km float, attractieparkgemiddeldaantalbinnen50km float, theatergemiddeldeafstandinkm float, theatergemiddeldaantalbinnen5km float, theatergemiddeldaantalbinnen10km float, theatergemiddeldaantalbinnen20km float, gemiddeldeafstandtotmuseum float, gemiddeldaantalmuseabinnen5km float, gemiddeldaantalmuseabinnen10km float, gemiddeldaantalmuseabinnen20km float, afstandtotopenbaargroentotaal float,
      afstandtotparkofplantsoen float, afstandtotdagrcreatiefterrein float, afstandtotbos float, afstandtotopennatuurterreintotaal float, afstandtotopendroognatuurterrein float, afstandtotopennatnatuurlijkterrein float, afstandtotsemiopenbaargroentotaal float, afstandtotsportterrein float, afstandtotvolkstuin float, afstandtotverblijfsrecreatiefterrein float, afstandtotrecreatiefbinnenwater float, afstandtotbegraafplaats float, jrstatcode text, jaar integer, fuuid text
    -> TestFilter_3
TestFilter_3
    DEFAULT_VALUE = <UNFILTERED>
    PASSED_TEST_GROUP_OUTPUT = FIRST
    TEST_LIST = "BOOL_OP,OR,COMPOSITE_TEST,""""""1"""""",TEST_CLAUSE,TEST @Value(buurtnaam) = Afrikaanderwijk",Afrikaanderwijk,"BOOL_OP,OR,COMPOSITE_TEST,""""""1"""""",TEST_CLAUSE,TEST @Value(buurtnaam) = Bloemhof",Bloemhof,"BOOL_OP,OR,COMPOSITE_TEST,""""""1"""""",TEST_CLAUSE,TEST @Value(buurtnaam) = Feijenoord",Feijenoord,"BOOL_OP,OR,COMPOSITE_TEST,""""""1"""""",TEST_CLAUSE,TEST @Value(buurtnaam) = Hillesluis",Hillesluis,"BOOL_OP,OR,COMPOSITE_TEST,""""""1"""""",TEST_CLAUSE,TEST @Value(buurtnaam) = Katendrecht",Katendrecht,"BOOL_OP,OR,COMPOSITE_TEST,""""""1"""""",TEST_CLAUSE,TEST @Value(buurtnaam) = Kop van Zuid",Kop van Zuid,"BOOL_OP,OR,COMPOSITE_TEST,""""""1"""""",TEST_CLAUSE,TEST @Value(buurtnaam) = Kop van Zuid - Entrepot",Kop van Zuid - Entrepot,"BOOL_OP,OR,COMPOSITE_TEST,""""""1"""""",TEST_CLAUSE,TEST @Value(buurtnaam) = Noordereiland",Noordereiland,"BOOL_OP,OR,COMPOSITE_TEST,""""""1"""""",TEST_CLAUSE,TEST @Value(buurtnaam) = Vreewijk",Vreewijk
    Afrikaanderwijk -> Afrikaanderwijk_Clipper [CLIPPER]
    Kop van Zuid -> Kop_Van_Zuid_Clipper [CLIPPER]
wijken (reader SPATIALITE_NATIVE_1)
    attributes: ogc_fid integer, wijkcode text, wijknaam text, gemeentecode text, gemeentenaam text, indelingswijzigingwijkenenbuurten integer, water text, omgevingsadressendichtheid integer, stedelijkheidadressenperkm2 integer, bevolkingsdichtheidinwonersperkm2 integer, aantalinwoners integer, mannen integer, vrouwen integer, percentagepersonen0tot15jaar integer, percentagepersonen15tot25jaar integer, percentagepersonen25tot45jaar integer, percentagepersonen45tot65jaar integer, percentagepersonen65jaarenouder integer, percentageongehuwd integer, percentagegehuwd integer, percentagegescheid integer, percentageverweduwd integer, geboortetotaal integer, geboortesper1000inwoners integer, sterftetotaal integer, sterfterelatief integer, aantalhuishoudens integer, percentageeenpersoonshuishoudens integer, percentagehuishoudenszonderkinderen integer, percentagehuishoudensmetkinderen integer,
      gemiddeldehuishoudsgrootte float, percentagemetherkomstlandnederland integer, percentagemetherkomstlanduiteuropaexclnl integer, percentagemetherkomstlandbuiteneuropa integer, percentagegebinnlmetherkomstlandnederland integer, percgebinnlmetherkomstlandineuropaexnl integer, percgebinnlmetherkomstlandbuiteneuropa integer, percgebbuitennlmetherkomstlndineuropaexnl integer, percgebbuitennlmetherkomstlndbuiteneuropa integer, aantalbedrijvenlandbouwbosbouwvisserij integer, aantalbedrijvennijverheidenergie integer, aantalbedrijvenhandelenhoreca integer, aantalbedrijvenvervoerinformatiecommunicatie integer, aantalbedrijvenfinancieelonroerendgoed integer, aantalbedrijvenzakelijkedienstverlening integer, aantalbedrijvenoverheidonderwijsenzorg integer, aantalbedrijvencultuurrecreatieoverige integer, aantalbedrijfsvestigingen integer, woningvoorraad integer, gemiddeldewoningwaarde integer, percentageeengezinswoning integer, percentagemeergezinswoning integer, percentagebewoond integer, percentagekoopwoningen integer, percentagehuurwoningen integer, perchuurwoningeninbezitwoningcorporaties integer, perchuurwoningeninbezitoverigeverhuurders integer, percentagewoningenmeteigendomonbekend integer, percentagebouwjaarklassetot2000 integer, percentagebouwjaarklassevanaf2000 integer,
      percentageleegstandwoningen integer, gemiddeldgasverbruiktotaal integer, gemiddeldgasverbruikappartement integer, gemiddeldgasverbruiktussenwoning integer, gemiddeldgasverbruikhoekwoning integer, gemiddeldgasverbruik2onder1kapwoning integer, gemiddeldgasverbruikvrijstaandewoning integer, gemiddeldgasverbruikhuurwoning integer, gemiddeldgasverbruikkoopwoning integer, gemiddeldelektriciteitsverbruiktotaal integer, gemiddeldelektriciteitsverbruikappartement integer, gemiddeldelektriciteitsverbruiktussenwoning integer, gemiddeldelektriciteitsverbruikhoekwoning integer, gemelektriciteitsverbruik2onder1kapwoning integer, gemelektriciteitsverbruikvrijstaandewoning integer, gemiddeldelektriciteitsverbruikhuurwoning integer, gemiddeldelektriciteitsverbruikkoopwoning integer, percentagewoningenmetstadsverwarming integer, opleidingsniveaulaag integer, opleidingsniveaumiddelbaar integer, opleidingsniveauhoog integer, nettoarbeidsparticipatie integer, percentagewerknemers integer, percentagezelfstandigen integer, aantalinkomensontvangers integer, gemiddeldinkomenperinkomensontvanger integer, gemiddeldinkomenperinwoner integer, percentagepersonenmethooginkomen integer, percentagepersonenmetlaaginkomen integer, percentagehuishoudensmethooginkomen integer,
      percentagehuishoudensmetlaaginkomen integer, percentagehuishoudensmetlaagsteinkomen integer, percentagehuishoudensonderofrondsociaalminimum integer, aantalpersonenmeteenaouitkeringtotaal integer, aantalpersonenmeteenwwuitkeringtotaal integer, aantalpersonenmeteenalgbijstandsuitkeringtot integer, aantalpersonenmeteenaowuitkeringtotaal integer, gemiddeldgestandaardiseerdinkomenvanhuishoudens float, huishoudenstot110percentvansociaalminimum float, huishoudenstot120percentvansociaalminimum float, mediaanvermogenvanparticulierehuish float, aantaljongerenmetjeugdzorginnatura integer, percentagejongerenmetjeugdzorginnatura float, aantalwmoclienten integer, aantalwmoclientenper1000inwoners integer, personenautostotaal integer, personenautosperhuishouden float, personenautosperkm2 integer, motortweewielerstotaal integer, aantalpersonenautosmetbrandstofbenzine integer, aantalpersonenautosmetoverigebrandstof integer, oppervlaktetotaalinha integer, oppervlaktelandinha integer, oppervlaktewaterinha integer, huisartsenpraktijkgemiddeldeafstandinkm float, huisartsenpraktijkgemiddeldaantalbinnen1km float, huisartsenpraktijkgemiddeldaantalbinnen3km float, huisartsenpraktijkgemiddeldaantalbinnen5km float, huisartsenpostgemiddeldeafstandinkm float, apotheekgemiddeldeafstandinkm float,
      ziekenhuisinclbuitenpolikliniekgemafstinkm float, ziekenhuisinclbuitenpoligemaantalbinnen5km float, ziekenhuisinclbuitenpoligemaantalbinnen10km float, ziekenhuisinclbuitenpoligemaantalbinnen20km float, ziekenhuisexclbuitenpolikliniekgemafstinkm float, ziekenhuisexclbuitenpoligemaantalbinnen5km float, ziekenhuisexclbuitenpoligemaantalbinnen10km float, ziekenhuisexclbuitenpoligemaantalbinnen20km float, grotesupermarktgemiddeldeafstandinkm float, grotesupermarktgemiddeldaantalbinnen1km float, grotesupermarktgemiddeldaantalbinnen3km float, grotesupermarktgemiddeldaantalbinnen5km float, winkelsovdagelijkselevensmgemafstinkm float, winkelsovdagellevensmgemaantalbinnen1km float, winkelsovdagellevensmgemaantalbinnen3km float, winkelsovdagellevensmgemaantalbinnen5km float, warenhuisgemiddeldeafstandinkm float, warenhuisgemiddeldaantalbinnen5km float, warenhuisgemiddeldaantalbinnen10km float, warenhuisgemiddeldaantalbinnen20km float, cafegemiddeldeafstandinkm float, cafegemiddeldaantalbinnen1km float, cafegemiddeldaantalbinnen3km float, cafegemiddeldaantalbinnen5km float, cafetariagemiddeldeafstandinkm float, cafetariagemiddeldaantalbinnen1km float, cafetariagemiddeldaantalbinnen3km float, cafetariagemiddeldaantalbinnen5km float, restaurantgemiddeldeafstandinkm float, restaurantgemiddeldaantalbinnen1km float,
      restaurantgemiddeldaantalbinnen3km float, restaurantgemiddeldaantalbinnen5km float, hotelgemiddeldeafstandinkm float, hotelgemiddeldaantalbinnen5km float, hotelgemiddeldaantalbinnen10km float, hotelgemiddeldaantalbinnen20km float, kinderdagverblijfgemiddeldeafstandinkm float, kinderdagverblijfgemiddeldaantalbinnen1km float, kinderdagverblijfgemiddeldaantalbinnen3km float, kinderdagverblijfgemiddeldaantalbinnen5km float, buitenschoolseopvanggemafstandinkm float, buitenschoolseopvanggemiddeldaantalbinnen1km float, buitenschoolseopvanggemiddeldaantalbinnen3km float, buitenschoolseopvanggemiddeldaantalbinnen5km float, basisonderwijsgemiddeldeafstandinkm float, basisonderwijsgemiddeldaantalbinnen1km float, basisonderwijsgemiddeldaantalbinnen3km float, basisonderwijsgemiddeldaantalbinnen5km float, voortgezetonderwijsgemafstandinkm float, voortgezetonderwijsgemiddeldaantalbinnen3km float, voortgezetonderwijsgemiddeldaantalbinnen5km float, voortgezetonderwijsgemiddeldaantalbinnen10km float, vmbogemiddeldeafstandinkm float, vmbogemiddeldaantalbinnen3km float, vmbogemiddeldaantalbinnen5km float, vmbogemiddeldaantalbinnen10km float, havovwogemiddeldeafstandinkm float, havovwogemiddeldaantalbinnen3km float, havovwogemiddeldaantalbinnen5km float, havovwogemiddeldaantalbinnen10km float,
      brandweerkazernegemiddeldeafstandinkm float, oprithoofdverkeersweggemiddeldeafstandinkm float, treinstationgemiddeldeafstandinkm float, overstapstationgemiddeldeafstandinkm float, zwembadgemiddeldeafstandinkm float, kunstijsbaangemiddeldeafstandinkm float, bibliotheekgemiddeldeafstandinkm float, poppodiumgemiddeldeafstandinkm float, bioscoopgemiddeldeafstandinkm float, bioscoopgemiddeldaantalbinnen5km float, bioscoopgemiddeldaantalbinnen10km float, bioscoopgemiddeldaantalbinnen20km float, saunagemiddeldeafstandinkm float, zonnebankgemiddeldeafstandinkm float, attractieparkgemiddeldeafstandinkm float, attractieparkgemiddeldaantalbinnen10km float, attractieparkgemiddeldaantalbinnen20km float, attractieparkgemiddeldaantalbinnen50km float, theatergemiddeldeafstandinkm float, theatergemiddeldaantalbinnen5km float, theatergemiddeldaantalbinnen10km float, theatergemiddeldaantalbinnen20km float, gemiddeldeafstandtotmuseum float, gemiddeldaantalmuseabinnen5km float, gemiddeldaantalmuseabinnen10km float, gemiddeldaantalmuseabinnen20km float, afstandtotopenbaargroentotaal float, afstandtotparkofplantsoen float, afstandtotdagrcreatiefterrein float, afstandtotbos float,
      afstandtotopennatuurterreintotaal float, afstandtotopendroognatuurterrein float, afstandtotopennatnatuurlijkterrein float, afstandtotsemiopenbaargroentotaal float, afstandtotsportterrein float, afstandtotvolkstuin float, afstandtotverblijfsrecreatiefterrein float, afstandtotrecreatiefbinnenwater float, afstandtotbegraafplaats float, jrstatcode text, jaar integer, fuuid text
    -> Clipper_4 [CLIPPER]
Clipper_4
    ADD_NODATA = YES
    BOUNDARY_CASES = INSIDE
    CLEANING_TOLERANCE_LOOKUP = AUTO
    CLIPPED_ATTR = _clipped
    CLIPPERS_FIRST = NO
    GENERATE_LIST = NO
    INVALID_PARTS_HANDLING = REJECT_WHOLE
    MISSING_M_MODE_LOOKUP = LINEAR
    MISSING_Z_MODE_LOOKUP = PLANAR
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    CLEANING_TOLERANCE = Automatic
    MISSING_M_MODE = Linear Interpolation
    MISSING_Z_MODE = Planar Interpolation
    INSIDE -> AttributeValueMapper_3
AttributeValueMapper_3
    LUT = Ailanthus,deciduous,Robinia,deciduous,Ulmus,deciduous,Platanus,deciduous,Tilia,deciduous,Prunus,deciduous,Gleditsia,deciduous,Fraxinus,deciduous,Liriodendron,deciduous,Liquidambar,deciduous,Betula,deciduous,Acer,deciduous,Alnus,deciduous,Crataegus,deciduous,Pyrus,deciduous,Malus,deciduous,Carpinus,deciduous,Sorbus,deciduous,Pterocarya,deciduous,Populus,deciduous,Salix,deciduous,Pinus,evergreen,Tetradium,deciduous,Aesculus,deciduous,Quercus,deciduous,Koelreuteria,deciduous,Corylus,deciduous,Ginkgo,deciduous,Magnolia,deciduous,Styphnolobium,deciduous,Syringa,deciduous,Cercidiphyllum,deciduous,Amelanchier,deciduous,Cercis,deciduous,Cornus,deciduous,Nyssa,deciduous,Catalpa,deciduous,assortiment,deciduous,Paulownia,deciduous,Larix,deciduous,Castanea,deciduous,Fagus,deciduous,Davidia,deciduous,Metasequoia,deciduous,Juglans,deciduous,Nothofagus,deciduous,Ilex,evergreen,Parrotia,deciduous,Ostrya,deciduous,Eucommia,deciduous,Cedrus,evergreen,Stewartia,deciduous,Thuja,evergreen,Rhus,deciduous,Ficus,deciduous,Morus,deciduous,Cladrastis,deciduous,Taxodium,deciduous,Gymnocladus,deciduous,Taxus,evergreen,Abies,evergreen,Hamamelis,deciduous,Carya,deciduous,Laburnum,deciduous,Toona,deciduous,Chitalpa,deciduous,Cupressocyparis,evergreen,Picea,evergreen,Styrax,deciduous,Celtis,deciduous,Chamaecyparis,evergreen,Arbutus,evergreen,Zelkova,deciduous,Sequoia,evergreen
    MAPPING_DIRECTION = FORWARD
    SRC = Geslacht
    VAL_ATTR = Type
    -> BoundsExtractor
BoundsExtractor
    XMAX = _xmax
    XMIN = _xmin
    YMAX = _ymax
    YMIN = _ymin
    ZMAX = _zmax
    ZMIN = _zmin
    -> SurfaceFootprintReplacer
SurfaceFootprintReplacer
    LIGHT_X = 0
    LIGHT_Y = 0
    LIGHT_Z = 1
    OFFSET_Z_LOOKUP = MIN_Z
    SHADOW_TYPE = DROP
    OFFSET_Z = Minimum Z
    SHADOW_MODE = Drop Shadow
    FOOTPRINT -> AttributeValueMapper
AttributeValueMapper
    LUT = @Value(_zmin),@Evaluate(@round(@Value(_zmin),1))
    MAPPING_DIRECTION = FORWARD
    SRC = _zmin
    VAL_ATTR = _zmin
    -> AttributeValueMapper_2
AttributeValueMapper_2
    LUT = @Value(_zmax),@Evaluate(@round(@Value(_zmax),1))
    MAPPING_DIRECTION = FORWARD
    SRC = _zmax
    VAL_ATTR = _zmax
    -> Kop_Van_Zuid_Clipper [CANDIDATE]
    -> Afrikaanderwijk_Clipper [CANDIDATE]
Afrikaanderwijk_Clipper: Clipper
    ADD_NODATA = YES
    BOUNDARY_CASES = INSIDE
    CLEANING_TOLERANCE_LOOKUP = AUTO
    CLIPPED_ATTR = _clipped
    CLIPPERS_FIRST = NO
    GENERATE_LIST = NO
    INVALID_PARTS_HANDLING = REJECT_WHOLE
    MISSING_M_MODE_LOOKUP = LINEAR
    MISSING_Z_MODE_LOOKUP = PLANAR
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    CLEANING_TOLERANCE = Automatic
    MISSING_M_MODE = Linear Interpolation
    MISSING_Z_MODE = Planar Interpolation
    INSIDE -> Clipper_2 [CANDIDATE]
    INSIDE -> Clipper_3 [CANDIDATE]
Clipper_3
    ADD_NODATA = YES
    BOUNDARY_CASES = INSIDE
    CLEANING_TOLERANCE_LOOKUP = AUTO
    CLIPPED_ATTR = _clipped
    CLIPPERS_FIRST = NO
    GENERATE_LIST = NO
    INVALID_PARTS_HANDLING = REJECT_WHOLE
    MISSING_M_MODE_LOOKUP = LINEAR
    MISSING_Z_MODE_LOOKUP = PLANAR
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    CLEANING_TOLERANCE = Automatic
    MISSING_M_MODE = Linear Interpolation
    MISSING_Z_MODE = Planar Interpolation
    OUTSIDE -> TestFilter_4
TestFilter_4
    DEFAULT_VALUE = <UNFILTERED>
    PASSED_TEST_GROUP_OUTPUT = FIRST
    TEST_LIST = "BOOL_OP,OR,COMPOSITE_TEST,""""""1"""""",TEST_CLAUSE,TEST @Value(Type) = deciduous",deciduous
    deciduous -> AttributeManager
    <UNFILTERED> -> 3DForcer
3DForcer
    KEEPZVAL = No
    ZVALATTR = @Value(_zmin)
    -> Table1 (writer SPATIALITE_NATIVE_5)
AttributeManager
    ATTR_TABLE = SET_TO citygml_crown_diameter (real64) = @mult(@Value(citygml_crown_diameter),0.64)
    -> CenterPointReplacer
CenterPointReplacer
    POINTTYPE = CENTER
    POINT -> Bufferer
Bufferer
    ANGLE = 30
    CAP_STYLE_LOOKUP = CAP_ROUND
    CORNER_STYLE_LOOKUP = JOIN_ROUND
    MODE = AREA
    OFFSET = @mult(@Value(citygml_crown_diameter),0.5)
    OFFSET_UNITS = METERS
    PRECISION = APPROX
    CAP_STYLE = Round
    CORNER_STYLE = Round
    BUFFERED -> 3DForcer_2
3DForcer_2
    KEEPZVAL = No
    ZVALATTR = @Value(_zmin)
    -> Table1 (writer SPATIALITE_NATIVE_5)
Table1 (writer SPATIALITE_NATIVE_5)
    attributes: gml_id text, gml_parent_id text, citygml_target_uri text, citygml_feature_role text, citygml_feature_role_attr_name text, citygml_feature_role_attr_val text, gml_description text, gml_name text, citygml_creationDate text, citygml_terminationDate text, externalReference{}.externalObject.name text, externalReference{}.externalObject.uri text, externalReference{}.informationSystem text, citygml_generalizes_to{}.xlink_href text, citygml_relative_to_terrain varchar(33), citygml_relative_to_water varchar(38), citygml_class text, citygml_class_codeSpace text, citygml_function{} text, citygml_function{}.codeSpace text, citygml_usage{} text, citygml_usage{}.codeSpace text, citygml_species text, citygml_species_codeSpace text, citygml_height double, citygml_height_units text, citygml_trunk_diameter double, citygml_trunk_diameter_units text, citygml_crown_diameter double, citygml_crown_diameter_units text,
      citygml_level_of_detail{} text, Aanlegjaar text, Beheerobjectomschrijving text, Boom_id text, Boomsortiment text, Boomsortiment_nederlands text, Boomstatus text, Brondatum text, Buurt text, Geslacht text, Hoogte text, Laatste_mutatie text, Ontwikkeling text, Stamdiameter text, Stamlengte text, Straat text, Thema text, Wijk text, tree_part text, _clipped varchar(3), Type text, _xmin double, _xmax double, _ymin double, _ymax double, _zmin double, _zmax double
Clipper_2
    ADD_NODATA = YES
    BOUNDARY_CASES = INSIDE
    CLEANING_TOLERANCE_LOOKUP = AUTO
    CLIPPED_ATTR = _clipped
    CLIPPERS_FIRST = NO
    GENERATE_LIST = NO
    INVALID_PARTS_HANDLING = REJECT_WHOLE
    MISSING_M_MODE_LOOKUP = LINEAR
    MISSING_Z_MODE_LOOKUP = PLANAR
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    CLEANING_TOLERANCE = Automatic
    MISSING_M_MODE = Linear Interpolation
    MISSING_Z_MODE = Planar Interpolation
    OUTSIDE -> Table1 (writer SPATIALITE_NATIVE_3)
Table1 (writer SPATIALITE_NATIVE_3)
    attributes: gml_id text, gml_parent_id text, citygml_target_uri text, citygml_feature_role text, citygml_feature_role_attr_name text, citygml_feature_role_attr_val text, gml_description text, gml_name text, citygml_creationDate text, citygml_terminationDate text, externalReference{}.externalObject.name text, externalReference{}.externalObject.uri text, externalReference{}.informationSystem text, citygml_generalizes_to{}.xlink_href text, citygml_relative_to_terrain varchar(33), citygml_relative_to_water varchar(38), citygml_class text, citygml_class_codeSpace text, citygml_function{} text, citygml_function{}.codeSpace text, citygml_usage{} text, citygml_usage{}.codeSpace text, citygml_species text, citygml_species_codeSpace text, citygml_height double, citygml_height_units text, citygml_trunk_diameter double, citygml_trunk_diameter_units text, citygml_crown_diameter double, citygml_crown_diameter_units text,
      citygml_level_of_detail{} text, Aanlegjaar text, Beheerobjectomschrijving text, Boom_id text, Boomsortiment text, Boomsortiment_nederlands text, Boomstatus text, Brondatum text, Buurt text, Geslacht text, Hoogte text, Laatste_mutatie text, Ontwikkeling text, Stamdiameter text, Stamlengte text, Straat text, Thema text, Wijk text, tree_part text, _clipped varchar(3), Type text, _xmin double, _xmax double, _ymin double, _ymax double, _zmin double, _zmax double
Kop_Van_Zuid_Clipper: Clipper
    ADD_NODATA = YES
    BOUNDARY_CASES = INSIDE
    CLEANING_TOLERANCE_LOOKUP = AUTO
    CLIPPED_ATTR = _clipped
    CLIPPERS_FIRST = NO
    GENERATE_LIST = NO
    INVALID_PARTS_HANDLING = REJECT_WHOLE
    MISSING_M_MODE_LOOKUP = LINEAR
    MISSING_Z_MODE_LOOKUP = PLANAR
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    CLEANING_TOLERANCE = Automatic
    MISSING_M_MODE = Linear Interpolation
    MISSING_Z_MODE = Planar Interpolation
    INSIDE -> Clipper_6 [CANDIDATE]
    INSIDE -> Clipper_5 [CANDIDATE]
Clipper_5
    ADD_NODATA = YES
    BOUNDARY_CASES = INSIDE
    CLEANING_TOLERANCE_LOOKUP = AUTO
    CLIPPED_ATTR = _clipped
    CLIPPERS_FIRST = NO
    GENERATE_LIST = NO
    INVALID_PARTS_HANDLING = REJECT_WHOLE
    MISSING_M_MODE_LOOKUP = LINEAR
    MISSING_Z_MODE_LOOKUP = PLANAR
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    CLEANING_TOLERANCE = Automatic
    MISSING_M_MODE = Linear Interpolation
    MISSING_Z_MODE = Planar Interpolation
    OUTSIDE -> TestFilter_9
TestFilter_9
    DEFAULT_VALUE = <UNFILTERED>
    PASSED_TEST_GROUP_OUTPUT = FIRST
    TEST_LIST = "BOOL_OP,OR,COMPOSITE_TEST,""""""1"""""",TEST_CLAUSE,TEST @Value(Type) = deciduous",deciduous
    deciduous -> AttributeManager_6
    <UNFILTERED> -> 3DForcer_3
AttributeManager_6
    ATTR_TABLE = SET_TO citygml_crown_diameter (real64) = @mult(@Value(citygml_crown_diameter),0.64)
    -> CenterPointReplacer_6
CenterPointReplacer_6
    POINTTYPE = CENTER
    POINT -> Bufferer_6
Bufferer_6
    ANGLE = 30
    CAP_STYLE_LOOKUP = CAP_ROUND
    CORNER_STYLE_LOOKUP = JOIN_ROUND
    MODE = AREA
    OFFSET = @mult(@Value(citygml_crown_diameter),0.5)
    OFFSET_UNITS = METERS
    PRECISION = APPROX
    CAP_STYLE = Round
    CORNER_STYLE = Round
    BUFFERED -> 3DForcer_4
3DForcer_4
    KEEPZVAL = No
    ZVALATTR = @Value(_zmin)
    -> Table1 (writer SPATIALITE_NATIVE_16)
3DForcer_3
    KEEPZVAL = No
    ZVALATTR = @Value(_zmin)
    -> Table1 (writer SPATIALITE_NATIVE_16)
Table1 (writer SPATIALITE_NATIVE_16)
    attributes: gml_id text, gml_parent_id text, citygml_target_uri text, citygml_feature_role text, citygml_feature_role_attr_name text, citygml_feature_role_attr_val text, gml_description text, gml_name text, citygml_creationDate text, citygml_terminationDate text, externalReference{}.externalObject.name text, externalReference{}.externalObject.uri text, externalReference{}.informationSystem text, citygml_generalizes_to{}.xlink_href text, citygml_relative_to_terrain varchar(33), citygml_relative_to_water varchar(38), citygml_class text, citygml_class_codeSpace text, citygml_function{} text, citygml_function{}.codeSpace text, citygml_usage{} text, citygml_usage{}.codeSpace text, citygml_species text, citygml_species_codeSpace text, citygml_height double, citygml_height_units text, citygml_trunk_diameter double, citygml_trunk_diameter_units text, citygml_crown_diameter double, citygml_crown_diameter_units text,
      citygml_level_of_detail{} text, Aanlegjaar text, Beheerobjectomschrijving text, Boom_id text, Boomsortiment text, Boomsortiment_nederlands text, Boomstatus text, Brondatum text, Buurt text, Geslacht text, Hoogte text, Laatste_mutatie text, Ontwikkeling text, Stamdiameter text, Stamlengte text, Straat text, Thema text, Wijk text, tree_part text, _clipped varchar(3), Type text, _xmin double, _xmax double, _ymin double, _ymax double, _zmin double, _zmax double
Clipper_6
    ADD_NODATA = YES
    BOUNDARY_CASES = INSIDE
    CLEANING_TOLERANCE_LOOKUP = AUTO
    CLIPPED_ATTR = _clipped
    CLIPPERS_FIRST = NO
    GENERATE_LIST = NO
    INVALID_PARTS_HANDLING = REJECT_WHOLE
    MISSING_M_MODE_LOOKUP = LINEAR
    MISSING_Z_MODE_LOOKUP = PLANAR
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    CLEANING_TOLERANCE = Automatic
    MISSING_M_MODE = Linear Interpolation
    MISSING_Z_MODE = Planar Interpolation
    OUTSIDE -> Table1 (writer SPATIALITE_NATIVE_15)
Table1 (writer SPATIALITE_NATIVE_15)
    attributes: gml_id text, gml_parent_id text, citygml_target_uri text, citygml_feature_role text, citygml_feature_role_attr_name text, citygml_feature_role_attr_val text, gml_description text, gml_name text, citygml_creationDate text, citygml_terminationDate text, externalReference{}.externalObject.name text, externalReference{}.externalObject.uri text, externalReference{}.informationSystem text, citygml_generalizes_to{}.xlink_href text, citygml_relative_to_terrain varchar(33), citygml_relative_to_water varchar(38), citygml_class text, citygml_class_codeSpace text, citygml_function{} text, citygml_function{}.codeSpace text, citygml_usage{} text, citygml_usage{}.codeSpace text, citygml_species text, citygml_species_codeSpace text, citygml_height double, citygml_height_units text, citygml_trunk_diameter double, citygml_trunk_diameter_units text, citygml_crown_diameter double, citygml_crown_diameter_units text,
      citygml_level_of_detail{} text, Aanlegjaar text, Beheerobjectomschrijving text, Boom_id text, Boomsortiment text, Boomsortiment_nederlands text, Boomstatus text, Brondatum text, Buurt text, Geslacht text, Hoogte text, Laatste_mutatie text, Ontwikkeling text, Stamdiameter text, Stamlengte text, Straat text, Thema text, Wijk text, tree_part text, _clipped varchar(3), Type text, _xmin double, _xmax double, _ymin double, _ymax double, _zmin double, _zmax double
CityModel (reader CITYGML_1)
    attributes: citygml_target_uri xml_buffer, gml_description xml_buffer, gml_name xml_buffer, citygml_city_object_member{}.xlink_href xml_buffer, gml_feature_member{}.xlink_href xml_buffer

FME custom transformer UniqueValueLogger
Description
This transformer lists all of the unique values for a chosen attribute alongside  a count attribute of the number of occurrences of each of these values. The information is logged in both the Translation Window / Workspace log file, and stored in attributes.
This transformer is useful when you are creating a workspace and need to know the possible values to use in a filter.
Input Ports
Input: This transformer accepts any features with an attribute.
Output Ports
Output: Features are output with the attribute selected as the unique value to filter, and a new attribute containing the number of occurrences of each unique value. All other attributes are removed. 
_count: Number of occurrences of each unique value.
_value: Unique values of selected attribute.
Parameters
Attribute to Analyze: Select the attribute for the transformer to run analysis on. 
Notes
Transformer alternatives:
Duplicate Filter - Consider using this transformer if you are looking to get a list of unique values and do not need a _count attribute 
StatisticsCalculator - Setting the Group By mode to the attribute to analyze will produce the same result as this transformer, it may beuse If you would like to gather other statistics as well as count of the unique attributes.

Parameters:
- VAL =   # Attribute to Analyze

Input (input)
    -> AttributeCreator

Bookmark: Count unique attribute values
AttributeCreator
    ATTR_TABLE = SET_TO _value = $(VAL)
    -> AttributeKeeper
Note: Remove unwanted / attributes
AttributeKeeper
    CREATE_BULK_MODE_FEATURES = NO
    KEEP_ATTRS = _value
    -> Aggregator
Note: Create aggregates of / features, grouped by / the target attribute value
Aggregator
    ACCUM_ATTRS = All
    AGGREGATE_TYPE = Homogeneous Collection (If Possible)
    COUNT_ATTR = _count
    GROUP_BY = _value
    MODE = Geometry - Assemble One Level
    SEP = ,
    ACCUM_ATTRS_NAME = Merge Incoming Attributes
    AGGREGATE -> StringConcatenator
Note: Concatenate unique values / with their occurrence counts
StringConcatenator
    ACTION = Create New Attribute
    PARM_LINE = fme_basicstring:14%1%14%1:@Value(_value),@Value(_count)
    VAL_ATTR = _concatenated
    -> Sorter
Note: Sort output based on / occurrence count and / attribute value
Sorter
    SORT_PARM = _count NUMERIC DESCENDING _value ALPHA ASCENDING
    SORTED -> ListBuilder
    SORTED -> AttributeManager

Bookmark: Create output
AttributeManager
    ATTR_TABLE = REMOVE _concatenated
    -> Output (output)
Output (output)

Bookmark: Log unique attribute values
Note: Turn all input features / Into a single list
ListBuilder
    LIST_NAME = _list
    -> ListConcatenator
Note: Concatenate values of / the list into an attribute
ListConcatenator
    DROP_EMPTY_PARTS = No
    LIST_ATTR = _list{}._concatenated
    VAL_ATTR = UNIQUE VALUES
    -> StringConcatenator_2
Note: Add header
StringConcatenator_2
    ACTION = Create New Attribute
    PARM_LINE = "\n\nVALUE, COUNT\n@Value(UNIQUE VALUES)\n"
    VAL_ATTR = UNIQUE VALUES
    -> AttributeRemover_2
Note: Remote the list
AttributeRemover_2
    LIST_ATTRS = _list{}
    -> Logger
Note: Log the single feature / that contains the / output attribute
Logger
    LOG_FEATURE = LOG_RECORD
    MAXCOORDS = 1
    MAXFEATS = 1
    MESSAGE = Unique values:
    SEVERITY = INFO
