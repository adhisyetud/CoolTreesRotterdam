FME workspace 4_proposing_sqltree.fmw

Parameters:
- SourceDataset_SPATIALITE_NATIVE = C:\MSc\Q2_2\Cooling_Rotterdam\Start_3\01_Input\Buurt_Feijenoord.sqlite   # SpatiaLite Database
- SourceDataset_SPATIALITE_NATIVE_28 = C:\MSc\Q2_2\Cooling_Rotterdam\Start_3\01_Input\Wijken_Feijenoord.sqlite   # SpatiaLite Database
- SourceDataset_SPATIALITE_NATIVE_27 = C:\MSc\Q2_2\Cooling_Rotterdam\Start_3\01_Input\BGT_Feijenoord\1_begroeidterreindeel.sqlite   # SpatiaLite Database
- SourceDataset_SPATIALITE_NATIVE_29 = C:\MSc\Q2_2\Cooling_Rotterdam\Start_3\01_Input\BGT_Feijenoord\2_onbegroeidterreindeel.sqlite   # SpatiaLite Database
- SourceDataset_SPATIALITE_NATIVE_31 = C:\MSc\Q2_2\Cooling_Rotterdam\Start_3\01_Input\BGT_Feijenoord\3_functioneelgebied.sqlite   # SpatiaLite Database
- SourceDataset_SPATIALITE_NATIVE_36 = C:\MSc\Q2_2\Cooling_Rotterdam\Start_3\01_Input\BGT_Feijenoord\5_wegdeel.sqlite   # SpatiaLite Database
- SourceDataset_SPATIALITE_NATIVE_30 = ""C:\MSc\Q2_2\Cooling_Rotterdam\Start_3\01_Input\BGT_Feijenoord\Afrikaanderwijk_Building.sqlite" "C:\MSc\Q2_2\Cooling_Rotterdam\Start_3\01_Input\BGT_Feijenoord\KVZ_Building.sqlite""   # SpatiaLite Database
- SourceDataset_SPATIALITE_NATIVE_17 = C:\MSc\Q2_2\Cooling_Rotterdam\Start_3\01_Input\BGT_Feijenoord\5_wegdeel.sqlite   # SpatiaLite Database
- SourceDataset_SPATIALITE_NATIVE_21 = C:\MSc\Q2_2\Cooling_Rotterdam\Start_3\01_Input\BGT_Feijenoord\6_waterdeel.sqlite   # SpatiaLite Database
- SourceDataset_SPATIALITE_NATIVE_19 = C:\MSc\Q2_2\Cooling_Rotterdam\Start_3\01_Input\BGT_Feijenoord\7_kast.sqlite   # SpatiaLite Database
- SourceDataset_SPATIALITE_NATIVE_23 = C:\MSc\Q2_2\Cooling_Rotterdam\Start_3\01_Input\BGT_Feijenoord\8_put.sqlite   # SpatiaLite Database
- SourceDataset_SPATIALITE_NATIVE_18 = C:\MSc\Q2_2\Cooling_Rotterdam\Start_3\01_Input\BGT_Feijenoord\9_mast.sqlite   # SpatiaLite Database
- SourceDataset_SPATIALITE_NATIVE_20 = C:\MSc\Q2_2\Cooling_Rotterdam\Start_3\01_Input\BGT_Feijenoord\10_paal.sqlite   # SpatiaLite Database
- SourceDataset_SPATIALITE_NATIVE_22 = C:\MSc\Q2_2\Cooling_Rotterdam\Start_3\01_Input\BGT_Feijenoord\11_vegetatieobject.sqlite   # SpatiaLite Database
- SourceDataset_SPATIALITE_NATIVE_26 = C:\MSc\Q2_2\Cooling_Rotterdam\Start_3\01_Input\BGT_Feijenoord\12_classified_cable_pipes.sqlite   # SpatiaLite Database
- DestDataset_SPATIALITE_NATIVE_2 = C:\MSc\Q2_2\Cooling_Rotterdam\Start_3\03_Intermediate_Results\2Buurt\PT\S\Round_PT_Afr_Summer.sqlite   # SpatiaLite Database
- DestDataset_SPATIALITE_NATIVE_3 = C:\MSc\Q2_2\Cooling_Rotterdam\Start_3\03_Intermediate_Results\2Buurt\PT\W\Round_PT_Kvz_Winter.sqlite   # SpatiaLite Database
- DestDataset_SPATIALITE_NATIVE_4 = C:\MSc\Q2_2\Cooling_Rotterdam\Start_3\03_Intermediate_Results\2Buurt\PT\W\Round_PT_Afr_Winter.sqlite   # SpatiaLite Database
- DestDataset_SPATIALITE_NATIVE_5 = C:\MSc\Q2_2\Cooling_Rotterdam\Start_3\03_Intermediate_Results\2Buurt\Suitable_Area_Trees\New folder\Suitable_Areas_Trees_AF.sqlite   # SpatiaLite Database
- DestDataset_SPATIALITE_NATIVE = C:\MSc\Q2_2\Cooling_Rotterdam\Start_3\03_Intermediate_Results\2Buurt\PT\S\Round_PT_Kvz_Summer.sqlite   # SpatiaLite Database

Readers:
- SPATIALITE_NATIVE_1: SPATIALITE_NATIVE from $(SourceDataset_SPATIALITE_NATIVE)
- SPATIALITE_NATIVE_2: SPATIALITE_NATIVE from $(SourceDataset_SPATIALITE_NATIVE_28)
- SPATIALITE_NATIVE_3: SPATIALITE_NATIVE from $(SourceDataset_SPATIALITE_NATIVE_27) in EPSG:28992
- SPATIALITE_NATIVE_4: SPATIALITE_NATIVE from $(SourceDataset_SPATIALITE_NATIVE_29) in EPSG:28992
- SPATIALITE_NATIVE_5: SPATIALITE_NATIVE from $(SourceDataset_SPATIALITE_NATIVE_31) in EPSG:28992
- SPATIALITE_NATIVE_6: SPATIALITE_NATIVE from $(SourceDataset_SPATIALITE_NATIVE_36) in EPSG:28992
- SPATIALITE_NATIVE_7: SPATIALITE_NATIVE from $(SourceDataset_SPATIALITE_NATIVE_30)
- SPATIALITE_NATIVE_8: SPATIALITE_NATIVE from $(SourceDataset_SPATIALITE_NATIVE_17) in EPSG:28992
- SPATIALITE_NATIVE_10: SPATIALITE_NATIVE from $(SourceDataset_SPATIALITE_NATIVE_21)
- SPATIALITE_NATIVE_11: SPATIALITE_NATIVE from $(SourceDataset_SPATIALITE_NATIVE_19)
- SPATIALITE_NATIVE_12: SPATIALITE_NATIVE from $(SourceDataset_SPATIALITE_NATIVE_23)
- SPATIALITE_NATIVE_13: SPATIALITE_NATIVE from $(SourceDataset_SPATIALITE_NATIVE_18)
- SPATIALITE_NATIVE_14: SPATIALITE_NATIVE from $(SourceDataset_SPATIALITE_NATIVE_20)
- SPATIALITE_NATIVE_15: SPATIALITE_NATIVE from $(SourceDataset_SPATIALITE_NATIVE_22)
- SPATIALITE_NATIVE_16: SPATIALITE_NATIVE from $(SourceDataset_SPATIALITE_NATIVE_26)

Writers:
- SPATIALITE_NATIVE_17: SPATIALITE_NATIVE to $(DestDataset_SPATIALITE_NATIVE_2)
- SPATIALITE_NATIVE_9: SPATIALITE_NATIVE to $(DestDataset_SPATIALITE_NATIVE)
- SPATIALITE_NATIVE_18: SPATIALITE_NATIVE to $(DestDataset_SPATIALITE_NATIVE_3)
- SPATIALITE_NATIVE_19: SPATIALITE_NATIVE to $(DestDataset_SPATIALITE_NATIVE_4)
- SPATIALITE_NATIVE_20: SPATIALITE_NATIVE to $(DestDataset_SPATIALITE_NATIVE_5)

Note: Impossible Areas: (+Buffer = 3m) / waterdeel = water surface
bgt_waterdeel__waterdeel (reader SPATIALITE_NATIVE_10)
    attributes: ogc_fid integer, gml_id text, creationdate varchar(10), lv_publicatiedatum varchar(19), relatievehoogteligging integer, inonderzoek integer, eindregistratie varchar(19), tijdstipregistratie varchar(23), namespace varchar(8), lokaalid varchar(38), bronhouder varchar(5), bgt_status varchar(8), plus_status varchar(10), class varchar(20), plus_type varchar(23), terminationdate varchar(10)
    -> Clipper_6 [CANDIDATE]
Note: Scenario 1, 2 = Buffer = 3m / Scenario 3, 4 = Buffer = 5m
Clipper_6
    ADD_NODATA = YES
    BOUNDARY_CASES = INSIDE
    CLEANING_TOLERANCE_LOOKUP = AUTO
    CLIPPED_ATTR = _clipped
    CLIPPERS_FIRST = NO
    GENERATE_LIST = NO
    INVALID_PARTS_HANDLING = REJECT_WHOLE
    MISSING_M_MODE_LOOKUP = LINEAR
    MISSING_Z_MODE_LOOKUP = PLANAR
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    CLEANING_TOLERANCE = Automatic
    MISSING_M_MODE = Linear Interpolation
    MISSING_Z_MODE = Planar Interpolation
    INSIDE -> Bufferer_2
Bufferer_2
    ANGLE = 22.5
    CAP_STYLE_LOOKUP = CAP_ARC
    CORNER_STYLE_LOOKUP = JOIN_ARC
    MODE = AREA
    OFFSET = 3
    OFFSET_UNITS = METERS
    PRECISION = APPROX
    CAP_STYLE = Arc
    CORNER_STYLE = Arc
    BUFFERED -> Dissolver_Impossible_Areas
Note: Impossible Areas: (+Buffer = +1.5m) / put = Pit, well, manhole / kast = Cabinet / enclosure (e.g., utility or telecom cabinet) / mast = Mast / tower (e.g., for lighting, telecom, or electricity) / paal = Pole (e.g., signpost, bollard, or light pole)
bgt_put__put (reader SPATIALITE_NATIVE_12)
    attributes: ogc_fid integer, gml_id text, creationdate varchar(10), lv_publicatiedatum varchar(19), relatievehoogteligging integer, inonderzoek integer, tijdstipregistratie varchar(23), namespace varchar(8), lokaalid varchar(38), bronhouder varchar(5), bgt_status varchar(8), plus_status varchar(10), function varchar(8), plus_type varchar(21), terminationdate varchar(10), eindregistratie varchar(19)
    -> Clipper_7 [CANDIDATE]
bgt_paal__paal (reader SPATIALITE_NATIVE_14)
    attributes: ogc_fid integer, gml_id text, creationdate varchar(10), lv_publicatiedatum varchar(19), relatievehoogteligging integer, inonderzoek integer, tijdstipregistratie varchar(23), namespace varchar(8), lokaalid varchar(38), bronhouder varchar(5), bgt_status varchar(8), plus_status varchar(10), function varchar(8), plus_type varchar(28), terminationdate varchar(10), eindregistratie varchar(19)
    -> Clipper_7 [CANDIDATE]
Note: Possible Areas: / onbegroeidterreindeel – "unvegetated terrain part"
bgt_onbegroeidterreindeel__onbegroeidterreindeel (reader SPATIALITE_NATIVE_4)
    attributes: ogc_fid integer, gml_id text, creationdate varchar(10), lv_publicatiedatum varchar(19), relatievehoogteligging integer, inonderzoek integer, tijdstipregistratie varchar(23), namespace varchar(8), lokaalid varchar(38), bronhouder varchar(5), bgt_status varchar(8), plus_status varchar(10), bgt_fysiekvoorkomen varchar(19), onbegroeidterreindeeloptalud integer, plus_fysiekvoorkomen varchar(17), kruinlijnonbegroeidterreindeel text, terminationdate varchar(10), eindregistratie varchar(19)
    -> Clipper_2 [CANDIDATE]
Note: Impossible Areas: (+Buffer = +3m) / existing trees
bgt_vegetatieobject__solitaryvegetationobject (reader SPATIALITE_NATIVE_15)
    attributes: ogc_fid integer, gml_id text, creationdate varchar(10), terminationdate varchar(10), lv_publicatiedatum varchar(19), relatievehoogteligging integer, inonderzoek integer, eindregistratie varchar(19), tijdstipregistratie varchar(23), namespace varchar(8), lokaalid varchar(38), bronhouder varchar(5), bgt_status varchar(8), plus_status varchar(10), class varchar(8), plus_type varchar(14)
    -> Clipper_8 [CANDIDATE]
Clipper_8
    ADD_NODATA = YES
    BOUNDARY_CASES = INSIDE
    CLEANING_TOLERANCE_LOOKUP = AUTO
    CLIPPED_ATTR = _clipped
    CLIPPERS_FIRST = NO
    GENERATE_LIST = NO
    INVALID_PARTS_HANDLING = REJECT_WHOLE
    MISSING_M_MODE_LOOKUP = LINEAR
    MISSING_Z_MODE_LOOKUP = PLANAR
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    CLEANING_TOLERANCE = Automatic
    MISSING_M_MODE = Linear Interpolation
    MISSING_Z_MODE = Planar Interpolation
    INSIDE -> Bufferer_4
Bufferer_4
    ANGLE = 22.5
    CAP_STYLE_LOOKUP = CAP_ROUND
    CORNER_STYLE_LOOKUP = JOIN_ARC
    MODE = AREA
    OFFSET = 3
    OFFSET_UNITS = METERS
    PRECISION = APPROX
    CAP_STYLE = Round
    CORNER_STYLE = Arc
    BUFFERED -> Dissolver_Impossible_Areas
Note: Possible Areas: / begroeidterreindeel – "vegetated terrain part"
bgt_begroeidterreindeel__plantcover (reader SPATIALITE_NATIVE_3)
    attributes: ogc_fid integer, gml_id text, creationdate varchar(10), lv_publicatiedatum varchar(19), relatievehoogteligging integer, inonderzoek integer, eindregistratie varchar(19), tijdstipregistratie varchar(23), namespace varchar(8), lokaalid varchar(38), bronhouder varchar(5), bgt_status varchar(8), plus_status varchar(10), class varchar(18), begroeidterreindeeloptalud integer, kruinlijnbegroeidterreindeel text, plus_fysiekvoorkomen varchar(22), terminationdate varchar(10)
    -> Clipper [CANDIDATE]
Note: Possible Areas: / hondenuitlaatplaats = Dog walking area / recreatie_park = Recreation: park / recreatie_speeltuin = Recreation: playground / recreatie_sportterrein = Recreation: sports field / recreatie_volkstuin = Recreation: allotment garden
bgt_functioneelgebied__functioneelgebied (reader SPATIALITE_NATIVE_5)
    attributes: ogc_fid integer, gml_id text, creationdate varchar(10), lv_publicatiedatum varchar(19), relatievehoogteligging integer, inonderzoek integer, tijdstipregistratie varchar(23), namespace varchar(8), lokaalid varchar(38), bronhouder varchar(5), bgt_status varchar(8), plus_status varchar(10), bgt_type varchar(8), plus_type varchar(39), naam varchar(27), eindregistratie varchar(19), terminationdate varchar(10)
    -> Clipper_3 [CANDIDATE]
bgt_kast__kast (reader SPATIALITE_NATIVE_11)
    attributes: ogc_fid integer, gml_id text, creationdate varchar(10), lv_publicatiedatum varchar(19), relatievehoogteligging integer, inonderzoek integer, tijdstipregistratie varchar(23), namespace varchar(8), lokaalid varchar(38), bronhouder varchar(5), bgt_status varchar(8), plus_status varchar(10), function varchar(8), plus_type varchar(14), eindregistratie varchar(19), terminationdate varchar(10)
    -> Clipper_7 [CANDIDATE]
bgt_mast__mast (reader SPATIALITE_NATIVE_13)
    attributes: ogc_fid integer, gml_id text, creationdate varchar(10), terminationdate varchar(10), lv_publicatiedatum varchar(19), relatievehoogteligging integer, inonderzoek integer, eindregistratie varchar(19), tijdstipregistratie varchar(23), namespace varchar(8), lokaalid varchar(38), bronhouder varchar(5), bgt_status varchar(8), plus_status varchar(10), function varchar(8), plus_type varchar(8)
    -> Clipper_7 [CANDIDATE]
Clipper_7
    ADD_NODATA = YES
    BOUNDARY_CASES = INSIDE
    CLEANING_TOLERANCE_LOOKUP = AUTO
    CLIPPED_ATTR = _clipped
    CLIPPERS_FIRST = NO
    GENERATE_LIST = NO
    INVALID_PARTS_HANDLING = REJECT_WHOLE
    MISSING_M_MODE_LOOKUP = LINEAR
    MISSING_Z_MODE_LOOKUP = PLANAR
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    CLEANING_TOLERANCE = Automatic
    MISSING_M_MODE = Linear Interpolation
    MISSING_Z_MODE = Planar Interpolation
    INSIDE -> Bufferer_3
Bufferer_3
    ANGLE = 22.5
    CAP_STYLE_LOOKUP = CAP_ROUND
    CORNER_STYLE_LOOKUP = JOIN_ARC
    MODE = AREA
    OFFSET = 1
    OFFSET_UNITS = METERS
    PRECISION = APPROX
    CAP_STYLE = Round
    CORNER_STYLE = Arc
    BUFFERED -> Dissolver_Impossible_Areas
Note: Possible Areas: / inrit = Driveway / entrance ramp / parkeervlak = Parking area / voetgangersgebied = Pedestrian zone / voetpad = Footpath / sidewalk / Impossible Areas: (+Buffer) / rijbaan_regionale_weg = Regional road carriageway (+Buffer = 7m) / overweg = Level crossing (+Buffer = 10m) / spoorbaan = Railway track (+Buffer = 10m) / OV_baan = Public transport lane (+Buffer = 3m) / voetpad_op_trap = Footpath on stairs (+Buffer = 3m) / fietspad = Bicycle path (+Buffer = 3m) / rijbaan_lokale_weg = Local road carriageway (+Buffer = 3m)
bgt_wegdeel__trafficarea (reader SPATIALITE_NATIVE_8)
    attributes: ogc_fid integer, gml_id text, creationdate varchar(10), lv_publicatiedatum varchar(19), relatievehoogteligging integer, inonderzoek integer, tijdstipregistratie varchar(23), namespace varchar(8), lokaalid varchar(38), bronhouder varchar(5), bgt_status varchar(8), plus_status varchar(10), function varchar(21), surfacematerial varchar(19), kruinlijnwegdeel text, wegdeeloptalud integer, plus_fysiekvoorkomenwegdeel varchar(17), plus_functiewegdeel varchar(15), eindregistratie varchar(19), terminationdate varchar(10)
    -> Clipper_5 [CANDIDATE]
Clipper_5
    ADD_NODATA = YES
    BOUNDARY_CASES = INSIDE
    CLEANING_TOLERANCE_LOOKUP = AUTO
    CLIPPED_ATTR = _clipped
    CLIPPERS_FIRST = NO
    GENERATE_LIST = NO
    INVALID_PARTS_HANDLING = REJECT_WHOLE
    MISSING_M_MODE_LOOKUP = LINEAR
    MISSING_Z_MODE_LOOKUP = PLANAR
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    CLEANING_TOLERANCE = Automatic
    MISSING_M_MODE = Linear Interpolation
    MISSING_Z_MODE = Planar Interpolation
    INSIDE -> TestFilter_2
TestFilter_2
    DEFAULT_VALUE = buffer
    PASSED_TEST_GROUP_OUTPUT = FIRST
    TEST_LIST = "BOOL_OP,OR,COMPOSITE_TEST,""""""1"""""",TEST_CLAUSE,TEST @Value(function) IN inrit,parkeervlak,voetgangersgebied,voetpad",green
    buffer -> TestFilter_5
TestFilter_5
    DEFAULT_VALUE = else
    PASSED_TEST_GROUP_OUTPUT = FIRST
    TEST_LIST = "BOOL_OP,OR,COMPOSITE_TEST,""""""1"""""",TEST_CLAUSE,TEST @Value(function) = fietspad",fitspad,"BOOL_OP,OR,COMPOSITE_TEST,""""""1"""""",TEST_CLAUSE,TEST @Value(function) = OV-baan",OV-baan,"BOOL_OP,OR,COMPOSITE_TEST,""""""1"""""",TEST_CLAUSE,TEST @Value(function) = overweg",overweg,"BOOL_OP,OR,COMPOSITE_TEST,""""""1"""""",TEST_CLAUSE,TEST @Value(function) = rijbaan lokale weg",rijbaan lokale weg,"BOOL_OP,OR,COMPOSITE_TEST,""""""1"""""",TEST_CLAUSE,TEST @Value(function) = rijbaan regionale weg",rijbaan regionale weg,"BOOL_OP,OR,COMPOSITE_TEST,""""""1"""""",TEST_CLAUSE,TEST @Value(function) = spoorbaan",spoorbaan,"BOOL_OP,OR,COMPOSITE_TEST,""""""1"""""",TEST_CLAUSE,TEST @Value(function) = voetpad op trap",voetpad op trap
    fitspad -> Bufferer_8
    OV-baan -> Bufferer_9
    overweg -> Bufferer_10
    rijbaan lokale weg -> Bufferer_11
    rijbaan regionale weg -> Bufferer_12
    spoorbaan -> Bufferer_13
    voetpad op trap -> Bufferer_14
Bufferer_8
    ANGLE = 22.5
    CAP_STYLE_LOOKUP = CAP_ROUND
    CORNER_STYLE_LOOKUP = JOIN_ARC
    MODE = AREA
    OFFSET = 3
    OFFSET_UNITS = METERS
    PRECISION = APPROX
    CAP_STYLE = Round
    CORNER_STYLE = Arc
    BUFFERED -> Dissolver_Impossible_Areas
Bufferer_9
    ANGLE = 22.5
    CAP_STYLE_LOOKUP = CAP_ROUND
    CORNER_STYLE_LOOKUP = JOIN_ARC
    MODE = AREA
    OFFSET = 3
    OFFSET_UNITS = METERS
    PRECISION = APPROX
    CAP_STYLE = Round
    CORNER_STYLE = Arc
    BUFFERED -> Dissolver_Impossible_Areas
Bufferer_10
    ANGLE = 22.5
    CAP_STYLE_LOOKUP = CAP_ROUND
    CORNER_STYLE_LOOKUP = JOIN_ARC
    MODE = AREA
    OFFSET = 10
    OFFSET_UNITS = METERS
    PRECISION = APPROX
    CAP_STYLE = Round
    CORNER_STYLE = Arc
    BUFFERED -> Dissolver_Impossible_Areas
Bufferer_11
    ANGLE = 22.5
    CAP_STYLE_LOOKUP = CAP_ROUND
    CORNER_STYLE_LOOKUP = JOIN_ARC
    MODE = AREA
    OFFSET = 3
    OFFSET_UNITS = METERS
    PRECISION = APPROX
    CAP_STYLE = Round
    CORNER_STYLE = Arc
    BUFFERED -> Dissolver_Impossible_Areas
Bufferer_12
    ANGLE = 22.5
    CAP_STYLE_LOOKUP = CAP_ROUND
    CORNER_STYLE_LOOKUP = JOIN_ARC
    MODE = AREA
    OFFSET = 10
    OFFSET_UNITS = METERS
    PRECISION = APPROX
    CAP_STYLE = Round
    CORNER_STYLE = Arc
    BUFFERED -> Dissolver_Impossible_Areas
Bufferer_13
    ANGLE = 22.5
    CAP_STYLE_LOOKUP = CAP_ROUND
    CORNER_STYLE_LOOKUP = JOIN_ARC
    MODE = AREA
    OFFSET = 10
    OFFSET_UNITS = METERS
    PRECISION = APPROX
    CAP_STYLE = Round
    CORNER_STYLE = Arc
    BUFFERED -> Dissolver_Impossible_Areas
Bufferer_14
    ANGLE = 22.5
    CAP_STYLE_LOOKUP = CAP_ROUND
    CORNER_STYLE_LOOKUP = JOIN_ARC
    MODE = AREA
    OFFSET = 3
    OFFSET_UNITS = METERS
    PRECISION = APPROX
    CAP_STYLE = Round
    CORNER_STYLE = Arc
    BUFFERED -> Dissolver_Impossible_Areas
Note: Impossible Areas: (+Buffer = +0.5m) / cables and pipes
feijenoord_cables__pipes (reader SPATIALITE_NATIVE_16)
    attributes: ogc_fid integer, groep varchar(9), klasse varchar(20), type varchar(50), lvzk_id integer, beheerder varchar(50), product varchar(20), pib integer, ruimtebesl float, status varchar(20), laag varchar(50), nivo integer, steuntekst varchar(50)
    -> Bufferer_7
Bufferer_7
    ANGLE = 22.5
    CAP_STYLE_LOOKUP = CAP_ROUND
    CORNER_STYLE_LOOKUP = JOIN_ARC
    MODE = AREA
    OFFSET = 0.5
    OFFSET_UNITS = METERS
    PRECISION = APPROX
    CAP_STYLE = Round
    CORNER_STYLE = Arc
    BUFFERED -> Bufferer_15
Bufferer_15
    ANGLE = 22.5
    CAP_STYLE_LOOKUP = CAP_ROUND
    CORNER_STYLE_LOOKUP = JOIN_ARC
    MODE = AREA
    OFFSET = 1
    OFFSET_UNITS = METERS
    PRECISION = APPROX
    CAP_STYLE = Round
    CORNER_STYLE = Arc
    BUFFERED -> Dissolver_Impossible_Areas
extracted_location (reader SPATIALITE_NATIVE_1)
    attributes: ogc_fid integer, buurtcode text, buurtnaam text, wijkcode text, gemeentecode text, gemeentenaam text, indelingswijzigingwijkenenbuurten integer, water text, meestvoorkomendepostcode text, dekkingspercentage integer, omgevingsadressendichtheid integer, stedelijkheidadressenperkm2 integer, bevolkingsdichtheidinwonersperkm2 integer, aantalinwoners integer, mannen integer, vrouwen integer, percentagepersonen0tot15jaar integer, percentagepersonen15tot25jaar integer, percentagepersonen25tot45jaar integer, percentagepersonen45tot65jaar integer, percentagepersonen65jaarenouder integer, percentageongehuwd integer, percentagegehuwd integer, percentagegescheid integer, percentageverweduwd integer, geboortetotaal integer, geboortesper1000inwoners integer, sterftetotaal integer, sterfterelatief integer, aantalhuishoudens integer,
      percentageeenpersoonshuishoudens integer, percentagehuishoudenszonderkinderen integer, percentagehuishoudensmetkinderen integer, gemiddeldehuishoudsgrootte float, percentagemetherkomstlandnederland integer, percentagemetherkomstlanduiteuropaexclnl integer, percentagemetherkomstlandbuiteneuropa integer, percentagegebinnlmetherkomstlandnederland integer, percgebinnlmetherkomstlandineuropaexnl integer, percgebinnlmetherkomstlandbuiteneuropa integer, percgebbuitennlmetherkomstlndineuropaexnl integer, percgebbuitennlmetherkomstlndbuiteneuropa integer, aantalbedrijvenlandbouwbosbouwvisserij integer, aantalbedrijvennijverheidenergie integer, aantalbedrijvenhandelenhoreca integer, aantalbedrijvenvervoerinformatiecommunicatie integer, aantalbedrijvenfinancieelonroerendgoed integer, aantalbedrijvenzakelijkedienstverlening integer, aantalbedrijvenoverheidonderwijsenzorg integer, aantalbedrijvencultuurrecreatieoverige integer, aantalbedrijfsvestigingen integer, woningvoorraad integer, gemiddeldewoningwaarde integer, percentageeengezinswoning integer, percentagemeergezinswoning integer, percentagebewoond integer, percentagekoopwoningen integer, percentagehuurwoningen integer, perchuurwoningeninbezitwoningcorporaties integer, perchuurwoningeninbezitoverigeverhuurders integer,
      percentagewoningenmeteigendomonbekend integer, percentagebouwjaarklassetot2000 integer, percentagebouwjaarklassevanaf2000 integer, percentageleegstandwoningen integer, gemiddeldgasverbruiktotaal integer, gemiddeldgasverbruikappartement integer, gemiddeldgasverbruiktussenwoning integer, gemiddeldgasverbruikhoekwoning integer, gemiddeldgasverbruik2onder1kapwoning integer, gemiddeldgasverbruikvrijstaandewoning integer, gemiddeldgasverbruikhuurwoning integer, gemiddeldgasverbruikkoopwoning integer, gemiddeldelektriciteitsverbruiktotaal integer, gemiddeldelektriciteitsverbruikappartement integer, gemiddeldelektriciteitsverbruiktussenwoning integer, gemiddeldelektriciteitsverbruikhoekwoning integer, gemelektriciteitsverbruik2onder1kapwoning integer, gemelektriciteitsverbruikvrijstaandewoning integer, gemiddeldelektriciteitsverbruikhuurwoning integer, gemiddeldelektriciteitsverbruikkoopwoning integer, percentagewoningenmetstadsverwarming integer, opleidingsniveaulaag integer, opleidingsniveaumiddelbaar integer, opleidingsniveauhoog integer, nettoarbeidsparticipatie integer, percentagewerknemers integer, percentagezelfstandigen integer, aantalinkomensontvangers integer, gemiddeldinkomenperinkomensontvanger integer, gemiddeldinkomenperinwoner integer,
      percentagepersonenmethooginkomen integer, percentagepersonenmetlaaginkomen integer, percentagehuishoudensmethooginkomen integer, percentagehuishoudensmetlaaginkomen integer, percentagehuishoudensmetlaagsteinkomen integer, percentagehuishoudensonderofrondsociaalminimum integer, aantalpersonenmeteenaouitkeringtotaal integer, aantalpersonenmeteenwwuitkeringtotaal integer, aantalpersonenmeteenalgbijstandsuitkeringtot integer, aantalpersonenmeteenaowuitkeringtotaal integer, gemiddeldgestandaardiseerdinkomenvanhuishoudens float, huishoudenstot110percentvansociaalminimum float, huishoudenstot120percentvansociaalminimum float, mediaanvermogenvanparticulierehuish float, aantaljongerenmetjeugdzorginnatura integer, percentagejongerenmetjeugdzorginnatura float, aantalwmoclienten integer, aantalwmoclientenper1000inwoners integer, personenautostotaal integer, personenautosperhuishouden float, personenautosperkm2 integer, motortweewielerstotaal integer, aantalpersonenautosmetbrandstofbenzine integer, aantalpersonenautosmetoverigebrandstof integer, oppervlaktetotaalinha integer, oppervlaktelandinha integer, oppervlaktewaterinha integer, huisartsenpraktijkgemiddeldeafstandinkm float, huisartsenpraktijkgemiddeldaantalbinnen1km float, huisartsenpraktijkgemiddeldaantalbinnen3km float,
      huisartsenpraktijkgemiddeldaantalbinnen5km float, huisartsenpostgemiddeldeafstandinkm float, apotheekgemiddeldeafstandinkm float, ziekenhuisinclbuitenpolikliniekgemafstinkm float, ziekenhuisinclbuitenpoligemaantalbinnen5km float, ziekenhuisinclbuitenpoligemaantalbinnen10km float, ziekenhuisinclbuitenpoligemaantalbinnen20km float, ziekenhuisexclbuitenpolikliniekgemafstinkm float, ziekenhuisexclbuitenpoligemaantalbinnen5km float, ziekenhuisexclbuitenpoligemaantalbinnen10km float, ziekenhuisexclbuitenpoligemaantalbinnen20km float, grotesupermarktgemiddeldeafstandinkm float, grotesupermarktgemiddeldaantalbinnen1km float, grotesupermarktgemiddeldaantalbinnen3km float, grotesupermarktgemiddeldaantalbinnen5km float, winkelsovdagelijkselevensmgemafstinkm float, winkelsovdagellevensmgemaantalbinnen1km float, winkelsovdagellevensmgemaantalbinnen3km float, winkelsovdagellevensmgemaantalbinnen5km float, warenhuisgemiddeldeafstandinkm float, warenhuisgemiddeldaantalbinnen5km float, warenhuisgemiddeldaantalbinnen10km float, warenhuisgemiddeldaantalbinnen20km float, cafegemiddeldeafstandinkm float, cafegemiddeldaantalbinnen1km float, cafegemiddeldaantalbinnen3km float, cafegemiddeldaantalbinnen5km float, cafetariagemiddeldeafstandinkm float, cafetariagemiddeldaantalbinnen1km float, cafetariagemiddeldaantalbinnen3km float,
      cafetariagemiddeldaantalbinnen5km float, restaurantgemiddeldeafstandinkm float, restaurantgemiddeldaantalbinnen1km float, restaurantgemiddeldaantalbinnen3km float, restaurantgemiddeldaantalbinnen5km float, hotelgemiddeldeafstandinkm float, hotelgemiddeldaantalbinnen5km float, hotelgemiddeldaantalbinnen10km float, hotelgemiddeldaantalbinnen20km float, kinderdagverblijfgemiddeldeafstandinkm float, kinderdagverblijfgemiddeldaantalbinnen1km float, kinderdagverblijfgemiddeldaantalbinnen3km float, kinderdagverblijfgemiddeldaantalbinnen5km float, buitenschoolseopvanggemafstandinkm float, buitenschoolseopvanggemiddeldaantalbinnen1km float, buitenschoolseopvanggemiddeldaantalbinnen3km float, buitenschoolseopvanggemiddeldaantalbinnen5km float, basisonderwijsgemiddeldeafstandinkm float, basisonderwijsgemiddeldaantalbinnen1km float, basisonderwijsgemiddeldaantalbinnen3km float, basisonderwijsgemiddeldaantalbinnen5km float, voortgezetonderwijsgemafstandinkm float, voortgezetonderwijsgemiddeldaantalbinnen3km float, voortgezetonderwijsgemiddeldaantalbinnen5km float, voortgezetonderwijsgemiddeldaantalbinnen10km float, vmbogemiddeldeafstandinkm float, vmbogemiddeldaantalbinnen3km float, vmbogemiddeldaantalbinnen5km float, vmbogemiddeldaantalbinnen10km float, havovwogemiddeldeafstandinkm float,
      havovwogemiddeldaantalbinnen3km float, havovwogemiddeldaantalbinnen5km float, havovwogemiddeldaantalbinnen10km float, brandweerkazernegemiddeldeafstandinkm float, oprithoofdverkeersweggemiddeldeafstandinkm float, treinstationgemiddeldeafstandinkm float, overstapstationgemiddeldeafstandinkm float, zwembadgemiddeldeafstandinkm float, kunstijsbaangemiddeldeafstandinkm float, bibliotheekgemiddeldeafstandinkm float, poppodiumgemiddeldeafstandinkm float, bioscoopgemiddeldeafstandinkm float, bioscoopgemiddeldaantalbinnen5km float, bioscoopgemiddeldaantalbinnen10km float, bioscoopgemiddeldaantalbinnen20km float, saunagemiddeldeafstandinkm float, zonnebankgemiddeldeafstandinkm float, attractieparkgemiddeldeafstandinkm float, attractieparkgemiddeldaantalbinnen10km float, attractieparkgemiddeldaantalbinnen20km float, attractieparkgemiddeldaantalbinnen50km float, theatergemiddeldeafstandinkm float, theatergemiddeldaantalbinnen5km float, theatergemiddeldaantalbinnen10km float, theatergemiddeldaantalbinnen20km float, gemiddeldeafstandtotmuseum float, gemiddeldaantalmuseabinnen5km float, gemiddeldaantalmuseabinnen10km float, gemiddeldaantalmuseabinnen20km float, afstandtotopenbaargroentotaal float,
      afstandtotparkofplantsoen float, afstandtotdagrcreatiefterrein float, afstandtotbos float, afstandtotopennatuurterreintotaal float, afstandtotopendroognatuurterrein float, afstandtotopennatnatuurlijkterrein float, afstandtotsemiopenbaargroentotaal float, afstandtotsportterrein float, afstandtotvolkstuin float, afstandtotverblijfsrecreatiefterrein float, afstandtotrecreatiefbinnenwater float, afstandtotbegraafplaats float, jrstatcode text, jaar integer, fuuid text
    -> TestFilter
TestFilter
    DEFAULT_VALUE = <UNFILTERED>
    PASSED_TEST_GROUP_OUTPUT = FIRST
    TEST_LIST = "BOOL_OP,OR,COMPOSITE_TEST,""""""1"""""",TEST_CLAUSE,TEST @Value(buurtnaam) = Kop van Zuid",@Value(buurtnaam) = Kop van Zuid,"BOOL_OP,OR,COMPOSITE_TEST,""""""1"""""",TEST_CLAUSE,TEST @Value(buurtnaam) = Afrikaanderwijk",@Value(buurtnaam) = Afrikaanderwijk
    @Value(buurtnaam) = Kop van Zuid -> Deaggregator
    @Value(buurtnaam) = Kop van Zuid -> Clipper_17 [CLIPPER]
    @Value(buurtnaam) = Afrikaanderwijk -> Deaggregator_2
    @Value(buurtnaam) = Afrikaanderwijk -> Clipper_18 [CLIPPER]
Deaggregator
    ATTR_ACCUM_MODE = HANDLE_CONFLICT
    ATTR_CONFLICT_RES = Use List Attribute Values
    EXPLODE_INSTANCES = No
    GEOM_LABEL_FIELD = _geometry_label
    LIST_ATTR_MODE_LOOKUP = LEAN
    PART_NUMBER_FIELD = _part_number
    RECURSIVE = No
    SPLIT_COMPOSITES = No
    DEAGGREGATED -> Tiler
Tiler
    CLEANING_TOLERANCE_LOOKUP = AUTO
    COLUMN_ATTR = _column
    DUPLICATE_ON_TILE_BORDERS = NO
    INVALID_PART_HANDLING = REJECT_WHOLE_FEATURE
    MISSING_MEASURE_VALUES_LOOKUP = LINEAR_INTERPOLATION
    MISSING_Z_VALUES_LOOKUP = PLANAR_INTERPOLATION
    ROW_ATTR = _row
    STARTINGCORNER = BOTTOM_LEFT
    TILE_HEIGHT = 3.5
    TILE_WIDTH = 3.5
    TILING_TYPE = TILE_SIZE
    CLEANING_TOLERANCE = Automatic
    MISSING_MEASURE_VALUES = Linear Interpolation
    MISSING_Z_VALUES = Planar Interpolation
    TILED -> CenterPointExtractor
CenterPointExtractor
    CENTX = _inside_x
    CENTY = _inside_y
    CENTZ = _inside_z
    EXTRACTIONMODE = CENTER
    -> VertexCreator
VertexCreator
    COORDSYS = EPSG:28992
    MEASURE_TYPE_LOOKUP = CONTINUOUS
    MODE = REPLACE
    REMOVE_ATTRIBUTES = Yes
    XVAL = @Value(_inside_x)
    YVAL = @Value(_inside_y)
    ZVAL = 2.5
    MEASURE_TYPE = Continuous
    MODE_NAME = Replace with Point
    -> AttributeManager
Note: Setting tree heights
AttributeManager
    ATTR_TABLE:
      SET_TO _inside_z (real64) = 2.5
      SET_TO _roof_z (real32) = 7.5
      REMOVE buurtcode (buffer)
      REMOVE buurtnaam (buffer)
      REMOVE wijkcode (buffer)
      REMOVE gemeentecode (buffer)
      REMOVE gemeentenaam (buffer)
      REMOVE indelingswijzigingwijkenenbuurten (int64)
      REMOVE water (buffer)
      REMOVE meestvoorkomendepostcode (buffer)
      REMOVE dekkingspercentage (int64)
      REMOVE omgevingsadressendichtheid (int64)
      REMOVE stedelijkheidadressenperkm2 (int64)
      REMOVE bevolkingsdichtheidinwonersperkm2 (int64)
      REMOVE aantalinwoners (int64)
      REMOVE mannen (int64)
      REMOVE vrouwen (int64)
      REMOVE percentagepersonen0tot15jaar (int64)
      REMOVE percentagepersonen15tot25jaar (int64)
      REMOVE percentagepersonen25tot45jaar (int64)
      REMOVE percentagepersonen45tot65jaar (int64)
      REMOVE percentagepersonen65jaarenouder (int64)
      REMOVE percentageongehuwd (int64)
      REMOVE percentagegehuwd (int64)
      REMOVE percentagegescheid (int64)
      REMOVE percentageverweduwd (int64)
      REMOVE geboortetotaal (int64)
      REMOVE geboortesper1000inwoners (int64)
      REMOVE sterftetotaal (int64)
      REMOVE sterfterelatief (int64)
      REMOVE aantalhuishoudens (int64)
      REMOVE percentageeenpersoonshuishoudens (int64)
      REMOVE percentagehuishoudenszonderkinderen (int64)
      REMOVE percentagehuishoudensmetkinderen (int64)
      REMOVE gemiddeldehuishoudsgrootte (real64)
      REMOVE percentagemetherkomstlandnederland (int64)
      REMOVE percentagemetherkomstlanduiteuropaexclnl (int64)
      REMOVE percentagemetherkomstlandbuiteneuropa (int64)
      REMOVE percentagegebinnlmetherkomstlandnederland (int64)
      REMOVE percgebinnlmetherkomstlandineuropaexnl (int64)
      REMOVE percgebinnlmetherkomstlandbuiteneuropa (int64)
      REMOVE percgebbuitennlmetherkomstlndineuropaexnl (int64)
      REMOVE percgebbuitennlmetherkomstlndbuiteneuropa (int64)
      REMOVE aantalbedrijvenlandbouwbosbouwvisserij (int64)
      REMOVE aantalbedrijvennijverheidenergie (int64)
      REMOVE aantalbedrijvenhandelenhoreca (int64)
      REMOVE aantalbedrijvenvervoerinformatiecommunicatie (int64)
      REMOVE aantalbedrijvenfinancieelonroerendgoed (int64)
      REMOVE aantalbedrijvenzakelijkedienstverlening (int64)
      REMOVE aantalbedrijvenoverheidonderwijsenzorg (int64)
      REMOVE aantalbedrijvencultuurrecreatieoverige (int64)
      REMOVE aantalbedrijfsvestigingen (int64)
      REMOVE woningvoorraad (int64)
      REMOVE gemiddeldewoningwaarde (int64)
      REMOVE percentageeengezinswoning (int64)
      REMOVE percentagemeergezinswoning (int64)
      REMOVE percentagebewoond (int64)
      REMOVE percentagekoopwoningen (int64)
      REMOVE percentagehuurwoningen (int64)
      REMOVE perchuurwoningeninbezitwoningcorporaties (int64)
      REMOVE perchuurwoningeninbezitoverigeverhuurders (int64)
      REMOVE percentagewoningenmeteigendomonbekend (int64)
      REMOVE percentagebouwjaarklassetot2000 (int64)
      REMOVE percentagebouwjaarklassevanaf2000 (int64)
      REMOVE percentageleegstandwoningen (int64)
      REMOVE gemiddeldgasverbruiktotaal (int64)
      REMOVE gemiddeldgasverbruikappartement (int64)
      REMOVE gemiddeldgasverbruiktussenwoning (int64)
      REMOVE gemiddeldgasverbruikhoekwoning (int64)
      REMOVE gemiddeldgasverbruik2onder1kapwoning (int64)
      REMOVE gemiddeldgasverbruikvrijstaandewoning (int64)
      REMOVE gemiddeldgasverbruikhuurwoning (int64)
      REMOVE gemiddeldgasverbruikkoopwoning (int64)
      REMOVE gemiddeldelektriciteitsverbruiktotaal (int64)
      REMOVE gemiddeldelektriciteitsverbruikappartement (int64)
      REMOVE gemiddeldelektriciteitsverbruiktussenwoning (int64)
      REMOVE gemiddeldelektriciteitsverbruikhoekwoning (int64)
      REMOVE gemelektriciteitsverbruik2onder1kapwoning (int64)
      REMOVE gemelektriciteitsverbruikvrijstaandewoning (int64)
      REMOVE gemiddeldelektriciteitsverbruikhuurwoning (int64)
      REMOVE gemiddeldelektriciteitsverbruikkoopwoning (int64)
      REMOVE percentagewoningenmetstadsverwarming (int64)
      REMOVE opleidingsniveaulaag (int64)
      REMOVE opleidingsniveaumiddelbaar (int64)
      REMOVE opleidingsniveauhoog (int64)
      REMOVE nettoarbeidsparticipatie (int64)
      REMOVE percentagewerknemers (int64)
      REMOVE percentagezelfstandigen (int64)
      REMOVE aantalinkomensontvangers (int64)
      REMOVE gemiddeldinkomenperinkomensontvanger (int64)
      REMOVE gemiddeldinkomenperinwoner (int64)
      REMOVE percentagepersonenmethooginkomen (int64)
      REMOVE percentagepersonenmetlaaginkomen (int64)
      REMOVE percentagehuishoudensmethooginkomen (int64)
      REMOVE percentagehuishoudensmetlaaginkomen (int64)
      REMOVE percentagehuishoudensmetlaagsteinkomen (int64)
      REMOVE percentagehuishoudensonderofrondsociaalminimum (int64)
      REMOVE aantalpersonenmeteenaouitkeringtotaal (int64)
      REMOVE aantalpersonenmeteenwwuitkeringtotaal (int64)
      REMOVE aantalpersonenmeteenalgbijstandsuitkeringtot (int64)
      REMOVE aantalpersonenmeteenaowuitkeringtotaal (int64)
      REMOVE gemiddeldgestandaardiseerdinkomenvanhuishoudens (real64)
      REMOVE huishoudenstot110percentvansociaalminimum (real64)
      REMOVE huishoudenstot120percentvansociaalminimum (real64)
      REMOVE mediaanvermogenvanparticulierehuish (real64)
      REMOVE aantaljongerenmetjeugdzorginnatura (int64)
      REMOVE percentagejongerenmetjeugdzorginnatura (real64)
      REMOVE aantalwmoclienten (int64)
      REMOVE aantalwmoclientenper1000inwoners (int64)
      REMOVE personenautostotaal (int64)
      REMOVE personenautosperhuishouden (real64)
      REMOVE personenautosperkm2 (int64)
      REMOVE motortweewielerstotaal (int64)
      REMOVE aantalpersonenautosmetbrandstofbenzine (int64)
      REMOVE aantalpersonenautosmetoverigebrandstof (int64)
      REMOVE oppervlaktetotaalinha (int64)
      REMOVE oppervlaktelandinha (int64)
      REMOVE oppervlaktewaterinha (int64)
      REMOVE huisartsenpraktijkgemiddeldeafstandinkm (real64)
      REMOVE huisartsenpraktijkgemiddeldaantalbinnen1km (real64)
      REMOVE huisartsenpraktijkgemiddeldaantalbinnen3km (real64)
      REMOVE huisartsenpraktijkgemiddeldaantalbinnen5km (real64)
      REMOVE huisartsenpostgemiddeldeafstandinkm (real64)
      REMOVE apotheekgemiddeldeafstandinkm (real64)
      REMOVE ziekenhuisinclbuitenpolikliniekgemafstinkm (real64)
      REMOVE ziekenhuisinclbuitenpoligemaantalbinnen5km (real64)
      REMOVE ziekenhuisinclbuitenpoligemaantalbinnen10km (real64)
      REMOVE ziekenhuisinclbuitenpoligemaantalbinnen20km (real64)
      REMOVE ziekenhuisexclbuitenpolikliniekgemafstinkm (real64)
      REMOVE ziekenhuisexclbuitenpoligemaantalbinnen5km (real64)
      REMOVE ziekenhuisexclbuitenpoligemaantalbinnen10km (real64)
      REMOVE ziekenhuisexclbuitenpoligemaantalbinnen20km (real64)
      REMOVE grotesupermarktgemiddeldeafstandinkm (real64)
      REMOVE grotesupermarktgemiddeldaantalbinnen1km (real64)
      REMOVE grotesupermarktgemiddeldaantalbinnen3km (real64)
      REMOVE grotesupermarktgemiddeldaantalbinnen5km (real64)
      REMOVE winkelsovdagelijkselevensmgemafstinkm (real64)
      REMOVE winkelsovdagellevensmgemaantalbinnen1km (real64)
      REMOVE winkelsovdagellevensmgemaantalbinnen3km (real64)
      REMOVE winkelsovdagellevensmgemaantalbinnen5km (real64)
      REMOVE warenhuisgemiddeldeafstandinkm (real64)
      REMOVE warenhuisgemiddeldaantalbinnen5km (real64)
      REMOVE warenhuisgemiddeldaantalbinnen10km (real64)
      REMOVE warenhuisgemiddeldaantalbinnen20km (real64)
      REMOVE cafegemiddeldeafstandinkm (real64)
      REMOVE cafegemiddeldaantalbinnen1km (real64)
      REMOVE cafegemiddeldaantalbinnen3km (real64)
      REMOVE cafegemiddeldaantalbinnen5km (real64)
      REMOVE cafetariagemiddeldeafstandinkm (real64)
      REMOVE cafetariagemiddeldaantalbinnen1km (real64)
      REMOVE cafetariagemiddeldaantalbinnen3km (real64)
      REMOVE cafetariagemiddeldaantalbinnen5km (real64)
      REMOVE restaurantgemiddeldeafstandinkm (real64)
      REMOVE restaurantgemiddeldaantalbinnen1km (real64)
      REMOVE restaurantgemiddeldaantalbinnen3km (real64)
      REMOVE restaurantgemiddeldaantalbinnen5km (real64)
      REMOVE hotelgemiddeldeafstandinkm (real64)
      REMOVE hotelgemiddeldaantalbinnen5km (real64)
      REMOVE hotelgemiddeldaantalbinnen10km (real64)
      REMOVE hotelgemiddeldaantalbinnen20km (real64)
      REMOVE kinderdagverblijfgemiddeldeafstandinkm (real64)
      REMOVE kinderdagverblijfgemiddeldaantalbinnen1km (real64)
      REMOVE kinderdagverblijfgemiddeldaantalbinnen3km (real64)
      REMOVE kinderdagverblijfgemiddeldaantalbinnen5km (real64)
      REMOVE buitenschoolseopvanggemafstandinkm (real64)
      REMOVE buitenschoolseopvanggemiddeldaantalbinnen1km (real64)
      REMOVE buitenschoolseopvanggemiddeldaantalbinnen3km (real64)
      REMOVE buitenschoolseopvanggemiddeldaantalbinnen5km (real64)
      REMOVE basisonderwijsgemiddeldeafstandinkm (real64)
      REMOVE basisonderwijsgemiddeldaantalbinnen1km (real64)
      REMOVE basisonderwijsgemiddeldaantalbinnen3km (real64)
      REMOVE basisonderwijsgemiddeldaantalbinnen5km (real64)
      REMOVE voortgezetonderwijsgemafstandinkm (real64)
      REMOVE voortgezetonderwijsgemiddeldaantalbinnen3km (real64)
      REMOVE voortgezetonderwijsgemiddeldaantalbinnen5km (real64)
      REMOVE voortgezetonderwijsgemiddeldaantalbinnen10km (real64)
      REMOVE vmbogemiddeldeafstandinkm (real64)
      REMOVE vmbogemiddeldaantalbinnen3km (real64)
      REMOVE vmbogemiddeldaantalbinnen5km (real64)
      REMOVE vmbogemiddeldaantalbinnen10km (real64)
      REMOVE havovwogemiddeldeafstandinkm (real64)
      REMOVE havovwogemiddeldaantalbinnen3km (real64)
      REMOVE havovwogemiddeldaantalbinnen5km (real64)
      REMOVE havovwogemiddeldaantalbinnen10km (real64)
      REMOVE brandweerkazernegemiddeldeafstandinkm (real64)
      REMOVE oprithoofdverkeersweggemiddeldeafstandinkm (real64)
      REMOVE treinstationgemiddeldeafstandinkm (real64)
      REMOVE overstapstationgemiddeldeafstandinkm (real64)
      REMOVE zwembadgemiddeldeafstandinkm (real64)
      REMOVE kunstijsbaangemiddeldeafstandinkm (real64)
      REMOVE bibliotheekgemiddeldeafstandinkm (real64)
      REMOVE poppodiumgemiddeldeafstandinkm (real64)
      REMOVE bioscoopgemiddeldeafstandinkm (real64)
      REMOVE bioscoopgemiddeldaantalbinnen5km (real64)
      REMOVE bioscoopgemiddeldaantalbinnen10km (real64)
      REMOVE bioscoopgemiddeldaantalbinnen20km (real64)
      REMOVE saunagemiddeldeafstandinkm (real64)
      REMOVE zonnebankgemiddeldeafstandinkm (real64)
      REMOVE attractieparkgemiddeldeafstandinkm (real64)
      REMOVE attractieparkgemiddeldaantalbinnen10km (real64)
      REMOVE attractieparkgemiddeldaantalbinnen20km (real64)
      REMOVE attractieparkgemiddeldaantalbinnen50km (real64)
      REMOVE theatergemiddeldeafstandinkm (real64)
      REMOVE theatergemiddeldaantalbinnen5km (real64)
      REMOVE theatergemiddeldaantalbinnen10km (real64)
      REMOVE theatergemiddeldaantalbinnen20km (real64)
      REMOVE gemiddeldeafstandtotmuseum (real64)
      REMOVE gemiddeldaantalmuseabinnen5km (real64)
      REMOVE gemiddeldaantalmuseabinnen10km (real64)
      REMOVE gemiddeldaantalmuseabinnen20km (real64)
      REMOVE afstandtotopenbaargroentotaal (real64)
      REMOVE afstandtotparkofplantsoen (real64)
      REMOVE afstandtotdagrcreatiefterrein (real64)
      REMOVE afstandtotbos (real64)
      REMOVE afstandtotopennatuurterreintotaal (real64)
      REMOVE afstandtotopendroognatuurterrein (real64)
      REMOVE afstandtotopennatnatuurlijkterrein (real64)
      REMOVE afstandtotsemiopenbaargroentotaal (real64)
      REMOVE afstandtotsportterrein (real64)
      REMOVE afstandtotvolkstuin (real64)
      REMOVE afstandtotverblijfsrecreatiefterrein (real64)
      REMOVE afstandtotrecreatiefbinnenwater (real64)
      REMOVE afstandtotbegraafplaats (real64)
      REMOVE jrstatcode (buffer)
      REMOVE jaar (int64)
      REMOVE fuuid (buffer)
    -> Clipper_11 [CANDIDATE]
Deaggregator_2
    ATTR_ACCUM_MODE = HANDLE_CONFLICT
    ATTR_CONFLICT_RES = Use List Attribute Values
    EXPLODE_INSTANCES = No
    GEOM_LABEL_FIELD = _geometry_label
    LIST_ATTR_MODE_LOOKUP = LEAN
    PART_NUMBER_FIELD = _part_number
    RECURSIVE = No
    SPLIT_COMPOSITES = No
    DEAGGREGATED -> Tiler_2
Tiler_2
    CLEANING_TOLERANCE_LOOKUP = AUTO
    COLUMN_ATTR = _column
    DUPLICATE_ON_TILE_BORDERS = NO
    INVALID_PART_HANDLING = REJECT_WHOLE_FEATURE
    MISSING_MEASURE_VALUES_LOOKUP = LINEAR_INTERPOLATION
    MISSING_Z_VALUES_LOOKUP = PLANAR_INTERPOLATION
    ROW_ATTR = _row
    STARTINGCORNER = BOTTOM_LEFT
    TILE_HEIGHT = 3.5
    TILE_WIDTH = 3.5
    TILING_TYPE = TILE_SIZE
    CLEANING_TOLERANCE = Automatic
    MISSING_MEASURE_VALUES = Linear Interpolation
    MISSING_Z_VALUES = Planar Interpolation
    TILED -> CenterPointExtractor_2
CenterPointExtractor_2
    CENTX = _inside_x
    CENTY = _inside_y
    CENTZ = _inside_z
    EXTRACTIONMODE = CENTER
    -> VertexCreator_2
VertexCreator_2
    COORDSYS = EPSG:28992
    MEASURE_TYPE_LOOKUP = CONTINUOUS
    MODE = REPLACE
    REMOVE_ATTRIBUTES = Yes
    XVAL = @Value(_inside_x)
    YVAL = @Value(_inside_y)
    ZVAL = 2.5
    MEASURE_TYPE = Continuous
    MODE_NAME = Replace with Point
    -> AttributeManager_2
AttributeManager_2
    ATTR_TABLE:
      SET_TO _inside_z (real64) = 2.5
      SET_TO _roof_z (real32) = 7.5
      REMOVE buurtcode (buffer)
      REMOVE buurtnaam (buffer)
      REMOVE wijkcode (buffer)
      REMOVE gemeentecode (buffer)
      REMOVE gemeentenaam (buffer)
      REMOVE indelingswijzigingwijkenenbuurten (int64)
      REMOVE water (buffer)
      REMOVE meestvoorkomendepostcode (buffer)
      REMOVE dekkingspercentage (int64)
      REMOVE omgevingsadressendichtheid (int64)
      REMOVE stedelijkheidadressenperkm2 (int64)
      REMOVE bevolkingsdichtheidinwonersperkm2 (int64)
      REMOVE aantalinwoners (int64)
      REMOVE mannen (int64)
      REMOVE vrouwen (int64)
      REMOVE percentagepersonen0tot15jaar (int64)
      REMOVE percentagepersonen15tot25jaar (int64)
      REMOVE percentagepersonen25tot45jaar (int64)
      REMOVE percentagepersonen45tot65jaar (int64)
      REMOVE percentagepersonen65jaarenouder (int64)
      REMOVE percentageongehuwd (int64)
      REMOVE percentagegehuwd (int64)
      REMOVE percentagegescheid (int64)
      REMOVE percentageverweduwd (int64)
      REMOVE geboortetotaal (int64)
      REMOVE geboortesper1000inwoners (int64)
      REMOVE sterftetotaal (int64)
      REMOVE sterfterelatief (int64)
      REMOVE aantalhuishoudens (int64)
      REMOVE percentageeenpersoonshuishoudens (int64)
      REMOVE percentagehuishoudenszonderkinderen (int64)
      REMOVE percentagehuishoudensmetkinderen (int64)
      REMOVE gemiddeldehuishoudsgrootte (real64)
      REMOVE percentagemetherkomstlandnederland (int64)
      REMOVE percentagemetherkomstlanduiteuropaexclnl (int64)
      REMOVE percentagemetherkomstlandbuiteneuropa (int64)
      REMOVE percentagegebinnlmetherkomstlandnederland (int64)
      REMOVE percgebinnlmetherkomstlandineuropaexnl (int64)
      REMOVE percgebinnlmetherkomstlandbuiteneuropa (int64)
      REMOVE percgebbuitennlmetherkomstlndineuropaexnl (int64)
      REMOVE percgebbuitennlmetherkomstlndbuiteneuropa (int64)
      REMOVE aantalbedrijvenlandbouwbosbouwvisserij (int64)
      REMOVE aantalbedrijvennijverheidenergie (int64)
      REMOVE aantalbedrijvenhandelenhoreca (int64)
      REMOVE aantalbedrijvenvervoerinformatiecommunicatie (int64)
      REMOVE aantalbedrijvenfinancieelonroerendgoed (int64)
      REMOVE aantalbedrijvenzakelijkedienstverlening (int64)
      REMOVE aantalbedrijvenoverheidonderwijsenzorg (int64)
      REMOVE aantalbedrijvencultuurrecreatieoverige (int64)
      REMOVE aantalbedrijfsvestigingen (int64)
      REMOVE woningvoorraad (int64)
      REMOVE gemiddeldewoningwaarde (int64)
      REMOVE percentageeengezinswoning (int64)
      REMOVE percentagemeergezinswoning (int64)
      REMOVE percentagebewoond (int64)
      REMOVE percentagekoopwoningen (int64)
      REMOVE percentagehuurwoningen (int64)
      REMOVE perchuurwoningeninbezitwoningcorporaties (int64)
      REMOVE perchuurwoningeninbezitoverigeverhuurders (int64)
      REMOVE percentagewoningenmeteigendomonbekend (int64)
      REMOVE percentagebouwjaarklassetot2000 (int64)
      REMOVE percentagebouwjaarklassevanaf2000 (int64)
      REMOVE percentageleegstandwoningen (int64)
      REMOVE gemiddeldgasverbruiktotaal (int64)
      REMOVE gemiddeldgasverbruikappartement (int64)
      REMOVE gemiddeldgasverbruiktussenwoning (int64)
      REMOVE gemiddeldgasverbruikhoekwoning (int64)
      REMOVE gemiddeldgasverbruik2onder1kapwoning (int64)
      REMOVE gemiddeldgasverbruikvrijstaandewoning (int64)
      REMOVE gemiddeldgasverbruikhuurwoning (int64)
      REMOVE gemiddeldgasverbruikkoopwoning (int64)
      REMOVE gemiddeldelektriciteitsverbruiktotaal (int64)
      REMOVE gemiddeldelektriciteitsverbruikappartement (int64)
      REMOVE gemiddeldelektriciteitsverbruiktussenwoning (int64)
      REMOVE gemiddeldelektriciteitsverbruikhoekwoning (int64)
      REMOVE gemelektriciteitsverbruik2onder1kapwoning (int64)
      REMOVE gemelektriciteitsverbruikvrijstaandewoning (int64)
      REMOVE gemiddeldelektriciteitsverbruikhuurwoning (int64)
      REMOVE gemiddeldelektriciteitsverbruikkoopwoning (int64)
      REMOVE percentagewoningenmetstadsverwarming (int64)
      REMOVE opleidingsniveaulaag (int64)
      REMOVE opleidingsniveaumiddelbaar (int64)
      REMOVE opleidingsniveauhoog (int64)
      REMOVE nettoarbeidsparticipatie (int64)
      REMOVE percentagewerknemers (int64)
      REMOVE percentagezelfstandigen (int64)
      REMOVE aantalinkomensontvangers (int64)
      REMOVE gemiddeldinkomenperinkomensontvanger (int64)
      REMOVE gemiddeldinkomenperinwoner (int64)
      REMOVE percentagepersonenmethooginkomen (int64)
      REMOVE percentagepersonenmetlaaginkomen (int64)
      REMOVE percentagehuishoudensmethooginkomen (int64)
      REMOVE percentagehuishoudensmetlaaginkomen (int64)
      REMOVE percentagehuishoudensmetlaagsteinkomen (int64)
      REMOVE percentagehuishoudensonderofrondsociaalminimum (int64)
      REMOVE aantalpersonenmeteenaouitkeringtotaal (int64)
      REMOVE aantalpersonenmeteenwwuitkeringtotaal (int64)
      REMOVE aantalpersonenmeteenalgbijstandsuitkeringtot (int64)
      REMOVE aantalpersonenmeteenaowuitkeringtotaal (int64)
      REMOVE gemiddeldgestandaardiseerdinkomenvanhuishoudens (real64)
      REMOVE huishoudenstot110percentvansociaalminimum (real64)
      REMOVE huishoudenstot120percentvansociaalminimum (real64)
      REMOVE mediaanvermogenvanparticulierehuish (real64)
      REMOVE aantaljongerenmetjeugdzorginnatura (int64)
      REMOVE percentagejongerenmetjeugdzorginnatura (real64)
      REMOVE aantalwmoclienten (int64)
      REMOVE aantalwmoclientenper1000inwoners (int64)
      REMOVE personenautostotaal (int64)
      REMOVE personenautosperhuishouden (real64)
      REMOVE personenautosperkm2 (int64)
      REMOVE motortweewielerstotaal (int64)
      REMOVE aantalpersonenautosmetbrandstofbenzine (int64)
      REMOVE aantalpersonenautosmetoverigebrandstof (int64)
      REMOVE oppervlaktetotaalinha (int64)
      REMOVE oppervlaktelandinha (int64)
      REMOVE oppervlaktewaterinha (int64)
      REMOVE huisartsenpraktijkgemiddeldeafstandinkm (real64)
      REMOVE huisartsenpraktijkgemiddeldaantalbinnen1km (real64)
      REMOVE huisartsenpraktijkgemiddeldaantalbinnen3km (real64)
      REMOVE huisartsenpraktijkgemiddeldaantalbinnen5km (real64)
      REMOVE huisartsenpostgemiddeldeafstandinkm (real64)
      REMOVE apotheekgemiddeldeafstandinkm (real64)
      REMOVE ziekenhuisinclbuitenpolikliniekgemafstinkm (real64)
      REMOVE ziekenhuisinclbuitenpoligemaantalbinnen5km (real64)
      REMOVE ziekenhuisinclbuitenpoligemaantalbinnen10km (real64)
      REMOVE ziekenhuisinclbuitenpoligemaantalbinnen20km (real64)
      REMOVE ziekenhuisexclbuitenpolikliniekgemafstinkm (real64)
      REMOVE ziekenhuisexclbuitenpoligemaantalbinnen5km (real64)
      REMOVE ziekenhuisexclbuitenpoligemaantalbinnen10km (real64)
      REMOVE ziekenhuisexclbuitenpoligemaantalbinnen20km (real64)
      REMOVE grotesupermarktgemiddeldeafstandinkm (real64)
      REMOVE grotesupermarktgemiddeldaantalbinnen1km (real64)
      REMOVE grotesupermarktgemiddeldaantalbinnen3km (real64)
      REMOVE grotesupermarktgemiddeldaantalbinnen5km (real64)
      REMOVE winkelsovdagelijkselevensmgemafstinkm (real64)
      REMOVE winkelsovdagellevensmgemaantalbinnen1km (real64)
      REMOVE winkelsovdagellevensmgemaantalbinnen3km (real64)
      REMOVE winkelsovdagellevensmgemaantalbinnen5km (real64)
      REMOVE warenhuisgemiddeldeafstandinkm (real64)
      REMOVE warenhuisgemiddeldaantalbinnen5km (real64)
      REMOVE warenhuisgemiddeldaantalbinnen10km (real64)
      REMOVE warenhuisgemiddeldaantalbinnen20km (real64)
      REMOVE cafegemiddeldeafstandinkm (real64)
      REMOVE cafegemiddeldaantalbinnen1km (real64)
      REMOVE cafegemiddeldaantalbinnen3km (real64)
      REMOVE cafegemiddeldaantalbinnen5km (real64)
      REMOVE cafetariagemiddeldeafstandinkm (real64)
      REMOVE cafetariagemiddeldaantalbinnen1km (real64)
      REMOVE cafetariagemiddeldaantalbinnen3km (real64)
      REMOVE cafetariagemiddeldaantalbinnen5km (real64)
      REMOVE restaurantgemiddeldeafstandinkm (real64)
      REMOVE restaurantgemiddeldaantalbinnen1km (real64)
      REMOVE restaurantgemiddeldaantalbinnen3km (real64)
      REMOVE restaurantgemiddeldaantalbinnen5km (real64)
      REMOVE hotelgemiddeldeafstandinkm (real64)
      REMOVE hotelgemiddeldaantalbinnen5km (real64)
      REMOVE hotelgemiddeldaantalbinnen10km (real64)
      REMOVE hotelgemiddeldaantalbinnen20km (real64)
      REMOVE kinderdagverblijfgemiddeldeafstandinkm (real64)
      REMOVE kinderdagverblijfgemiddeldaantalbinnen1km (real64)
      REMOVE kinderdagverblijfgemiddeldaantalbinnen3km (real64)
      REMOVE kinderdagverblijfgemiddeldaantalbinnen5km (real64)
      REMOVE buitenschoolseopvanggemafstandinkm (real64)
      REMOVE buitenschoolseopvanggemiddeldaantalbinnen1km (real64)
      REMOVE buitenschoolseopvanggemiddeldaantalbinnen3km (real64)
      REMOVE buitenschoolseopvanggemiddeldaantalbinnen5km (real64)
      REMOVE basisonderwijsgemiddeldeafstandinkm (real64)
      REMOVE basisonderwijsgemiddeldaantalbinnen1km (real64)
      REMOVE basisonderwijsgemiddeldaantalbinnen3km (real64)
      REMOVE basisonderwijsgemiddeldaantalbinnen5km (real64)
      REMOVE voortgezetonderwijsgemafstandinkm (real64)
      REMOVE voortgezetonderwijsgemiddeldaantalbinnen3km (real64)
      REMOVE voortgezetonderwijsgemiddeldaantalbinnen5km (real64)
      REMOVE voortgezetonderwijsgemiddeldaantalbinnen10km (real64)
      REMOVE vmbogemiddeldeafstandinkm (real64)
      REMOVE vmbogemiddeldaantalbinnen3km (real64)
      REMOVE vmbogemiddeldaantalbinnen5km (real64)
      REMOVE vmbogemiddeldaantalbinnen10km (real64)
      REMOVE havovwogemiddeldeafstandinkm (real64)
      REMOVE havovwogemiddeldaantalbinnen3km (real64)
      REMOVE havovwogemiddeldaantalbinnen5km (real64)
      REMOVE havovwogemiddeldaantalbinnen10km (real64)
      REMOVE brandweerkazernegemiddeldeafstandinkm (real64)
      REMOVE oprithoofdverkeersweggemiddeldeafstandinkm (real64)
      REMOVE treinstationgemiddeldeafstandinkm (real64)
      REMOVE overstapstationgemiddeldeafstandinkm (real64)
      REMOVE zwembadgemiddeldeafstandinkm (real64)
      REMOVE kunstijsbaangemiddeldeafstandinkm (real64)
      REMOVE bibliotheekgemiddeldeafstandinkm (real64)
      REMOVE poppodiumgemiddeldeafstandinkm (real64)
      REMOVE bioscoopgemiddeldeafstandinkm (real64)
      REMOVE bioscoopgemiddeldaantalbinnen5km (real64)
      REMOVE bioscoopgemiddeldaantalbinnen10km (real64)
      REMOVE bioscoopgemiddeldaantalbinnen20km (real64)
      REMOVE saunagemiddeldeafstandinkm (real64)
      REMOVE zonnebankgemiddeldeafstandinkm (real64)
      REMOVE attractieparkgemiddeldeafstandinkm (real64)
      REMOVE attractieparkgemiddeldaantalbinnen10km (real64)
      REMOVE attractieparkgemiddeldaantalbinnen20km (real64)
      REMOVE attractieparkgemiddeldaantalbinnen50km (real64)
      REMOVE theatergemiddeldeafstandinkm (real64)
      REMOVE theatergemiddeldaantalbinnen5km (real64)
      REMOVE theatergemiddeldaantalbinnen10km (real64)
      REMOVE theatergemiddeldaantalbinnen20km (real64)
      REMOVE gemiddeldeafstandtotmuseum (real64)
      REMOVE gemiddeldaantalmuseabinnen5km (real64)
      REMOVE gemiddeldaantalmuseabinnen10km (real64)
      REMOVE gemiddeldaantalmuseabinnen20km (real64)
      REMOVE afstandtotopenbaargroentotaal (real64)
      REMOVE afstandtotparkofplantsoen (real64)
      REMOVE afstandtotdagrcreatiefterrein (real64)
      REMOVE afstandtotbos (real64)
      REMOVE afstandtotopennatuurterreintotaal (real64)
      REMOVE afstandtotopendroognatuurterrein (real64)
      REMOVE afstandtotopennatnatuurlijkterrein (real64)
      REMOVE afstandtotsemiopenbaargroentotaal (real64)
      REMOVE afstandtotsportterrein (real64)
      REMOVE afstandtotvolkstuin (real64)
      REMOVE afstandtotverblijfsrecreatiefterrein (real64)
      REMOVE afstandtotrecreatiefbinnenwater (real64)
      REMOVE afstandtotbegraafplaats (real64)
      REMOVE jrstatcode (buffer)
      REMOVE jaar (int64)
      REMOVE fuuid (buffer)
    -> Clipper_12 [CANDIDATE]
wijken (reader SPATIALITE_NATIVE_2)
    attributes: ogc_fid integer, wijkcode text, wijknaam text, gemeentecode text, gemeentenaam text, indelingswijzigingwijkenenbuurten integer, water text, omgevingsadressendichtheid integer, stedelijkheidadressenperkm2 integer, bevolkingsdichtheidinwonersperkm2 integer, aantalinwoners integer, mannen integer, vrouwen integer, percentagepersonen0tot15jaar integer, percentagepersonen15tot25jaar integer, percentagepersonen25tot45jaar integer, percentagepersonen45tot65jaar integer, percentagepersonen65jaarenouder integer, percentageongehuwd integer, percentagegehuwd integer, percentagegescheid integer, percentageverweduwd integer, geboortetotaal integer, geboortesper1000inwoners integer, sterftetotaal integer, sterfterelatief integer, aantalhuishoudens integer, percentageeenpersoonshuishoudens integer, percentagehuishoudenszonderkinderen integer, percentagehuishoudensmetkinderen integer,
      gemiddeldehuishoudsgrootte float, percentagemetherkomstlandnederland integer, percentagemetherkomstlanduiteuropaexclnl integer, percentagemetherkomstlandbuiteneuropa integer, percentagegebinnlmetherkomstlandnederland integer, percgebinnlmetherkomstlandineuropaexnl integer, percgebinnlmetherkomstlandbuiteneuropa integer, percgebbuitennlmetherkomstlndineuropaexnl integer, percgebbuitennlmetherkomstlndbuiteneuropa integer, aantalbedrijvenlandbouwbosbouwvisserij integer, aantalbedrijvennijverheidenergie integer, aantalbedrijvenhandelenhoreca integer, aantalbedrijvenvervoerinformatiecommunicatie integer, aantalbedrijvenfinancieelonroerendgoed integer, aantalbedrijvenzakelijkedienstverlening integer, aantalbedrijvenoverheidonderwijsenzorg integer, aantalbedrijvencultuurrecreatieoverige integer, aantalbedrijfsvestigingen integer, woningvoorraad integer, gemiddeldewoningwaarde integer, percentageeengezinswoning integer, percentagemeergezinswoning integer, percentagebewoond integer, percentagekoopwoningen integer, percentagehuurwoningen integer, perchuurwoningeninbezitwoningcorporaties integer, perchuurwoningeninbezitoverigeverhuurders integer, percentagewoningenmeteigendomonbekend integer, percentagebouwjaarklassetot2000 integer, percentagebouwjaarklassevanaf2000 integer,
      percentageleegstandwoningen integer, gemiddeldgasverbruiktotaal integer, gemiddeldgasverbruikappartement integer, gemiddeldgasverbruiktussenwoning integer, gemiddeldgasverbruikhoekwoning integer, gemiddeldgasverbruik2onder1kapwoning integer, gemiddeldgasverbruikvrijstaandewoning integer, gemiddeldgasverbruikhuurwoning integer, gemiddeldgasverbruikkoopwoning integer, gemiddeldelektriciteitsverbruiktotaal integer, gemiddeldelektriciteitsverbruikappartement integer, gemiddeldelektriciteitsverbruiktussenwoning integer, gemiddeldelektriciteitsverbruikhoekwoning integer, gemelektriciteitsverbruik2onder1kapwoning integer, gemelektriciteitsverbruikvrijstaandewoning integer, gemiddeldelektriciteitsverbruikhuurwoning integer, gemiddeldelektriciteitsverbruikkoopwoning integer, percentagewoningenmetstadsverwarming integer, opleidingsniveaulaag integer, opleidingsniveaumiddelbaar integer, opleidingsniveauhoog integer, nettoarbeidsparticipatie integer, percentagewerknemers integer, percentagezelfstandigen integer, aantalinkomensontvangers integer, gemiddeldinkomenperinkomensontvanger integer, gemiddeldinkomenperinwoner integer, percentagepersonenmethooginkomen integer, percentagepersonenmetlaaginkomen integer, percentagehuishoudensmethooginkomen integer,
      percentagehuishoudensmetlaaginkomen integer, percentagehuishoudensmetlaagsteinkomen integer, percentagehuishoudensonderofrondsociaalminimum integer, aantalpersonenmeteenaouitkeringtotaal integer, aantalpersonenmeteenwwuitkeringtotaal integer, aantalpersonenmeteenalgbijstandsuitkeringtot integer, aantalpersonenmeteenaowuitkeringtotaal integer, gemiddeldgestandaardiseerdinkomenvanhuishoudens float, huishoudenstot110percentvansociaalminimum float, huishoudenstot120percentvansociaalminimum float, mediaanvermogenvanparticulierehuish float, aantaljongerenmetjeugdzorginnatura integer, percentagejongerenmetjeugdzorginnatura float, aantalwmoclienten integer, aantalwmoclientenper1000inwoners integer, personenautostotaal integer, personenautosperhuishouden float, personenautosperkm2 integer, motortweewielerstotaal integer, aantalpersonenautosmetbrandstofbenzine integer, aantalpersonenautosmetoverigebrandstof integer, oppervlaktetotaalinha integer, oppervlaktelandinha integer, oppervlaktewaterinha integer, huisartsenpraktijkgemiddeldeafstandinkm float, huisartsenpraktijkgemiddeldaantalbinnen1km float, huisartsenpraktijkgemiddeldaantalbinnen3km float, huisartsenpraktijkgemiddeldaantalbinnen5km float, huisartsenpostgemiddeldeafstandinkm float, apotheekgemiddeldeafstandinkm float,
      ziekenhuisinclbuitenpolikliniekgemafstinkm float, ziekenhuisinclbuitenpoligemaantalbinnen5km float, ziekenhuisinclbuitenpoligemaantalbinnen10km float, ziekenhuisinclbuitenpoligemaantalbinnen20km float, ziekenhuisexclbuitenpolikliniekgemafstinkm float, ziekenhuisexclbuitenpoligemaantalbinnen5km float, ziekenhuisexclbuitenpoligemaantalbinnen10km float, ziekenhuisexclbuitenpoligemaantalbinnen20km float, grotesupermarktgemiddeldeafstandinkm float, grotesupermarktgemiddeldaantalbinnen1km float, grotesupermarktgemiddeldaantalbinnen3km float, grotesupermarktgemiddeldaantalbinnen5km float, winkelsovdagelijkselevensmgemafstinkm float, winkelsovdagellevensmgemaantalbinnen1km float, winkelsovdagellevensmgemaantalbinnen3km float, winkelsovdagellevensmgemaantalbinnen5km float, warenhuisgemiddeldeafstandinkm float, warenhuisgemiddeldaantalbinnen5km float, warenhuisgemiddeldaantalbinnen10km float, warenhuisgemiddeldaantalbinnen20km float, cafegemiddeldeafstandinkm float, cafegemiddeldaantalbinnen1km float, cafegemiddeldaantalbinnen3km float, cafegemiddeldaantalbinnen5km float, cafetariagemiddeldeafstandinkm float, cafetariagemiddeldaantalbinnen1km float, cafetariagemiddeldaantalbinnen3km float, cafetariagemiddeldaantalbinnen5km float, restaurantgemiddeldeafstandinkm float, restaurantgemiddeldaantalbinnen1km float,
      restaurantgemiddeldaantalbinnen3km float, restaurantgemiddeldaantalbinnen5km float, hotelgemiddeldeafstandinkm float, hotelgemiddeldaantalbinnen5km float, hotelgemiddeldaantalbinnen10km float, hotelgemiddeldaantalbinnen20km float, kinderdagverblijfgemiddeldeafstandinkm float, kinderdagverblijfgemiddeldaantalbinnen1km float, kinderdagverblijfgemiddeldaantalbinnen3km float, kinderdagverblijfgemiddeldaantalbinnen5km float, buitenschoolseopvanggemafstandinkm float, buitenschoolseopvanggemiddeldaantalbinnen1km float, buitenschoolseopvanggemiddeldaantalbinnen3km float, buitenschoolseopvanggemiddeldaantalbinnen5km float, basisonderwijsgemiddeldeafstandinkm float, basisonderwijsgemiddeldaantalbinnen1km float, basisonderwijsgemiddeldaantalbinnen3km float, basisonderwijsgemiddeldaantalbinnen5km float, voortgezetonderwijsgemafstandinkm float, voortgezetonderwijsgemiddeldaantalbinnen3km float, voortgezetonderwijsgemiddeldaantalbinnen5km float, voortgezetonderwijsgemiddeldaantalbinnen10km float, vmbogemiddeldeafstandinkm float, vmbogemiddeldaantalbinnen3km float, vmbogemiddeldaantalbinnen5km float, vmbogemiddeldaantalbinnen10km float, havovwogemiddeldeafstandinkm float, havovwogemiddeldaantalbinnen3km float, havovwogemiddeldaantalbinnen5km float, havovwogemiddeldaantalbinnen10km float,
      brandweerkazernegemiddeldeafstandinkm float, oprithoofdverkeersweggemiddeldeafstandinkm float, treinstationgemiddeldeafstandinkm float, overstapstationgemiddeldeafstandinkm float, zwembadgemiddeldeafstandinkm float, kunstijsbaangemiddeldeafstandinkm float, bibliotheekgemiddeldeafstandinkm float, poppodiumgemiddeldeafstandinkm float, bioscoopgemiddeldeafstandinkm float, bioscoopgemiddeldaantalbinnen5km float, bioscoopgemiddeldaantalbinnen10km float, bioscoopgemiddeldaantalbinnen20km float, saunagemiddeldeafstandinkm float, zonnebankgemiddeldeafstandinkm float, attractieparkgemiddeldeafstandinkm float, attractieparkgemiddeldaantalbinnen10km float, attractieparkgemiddeldaantalbinnen20km float, attractieparkgemiddeldaantalbinnen50km float, theatergemiddeldeafstandinkm float, theatergemiddeldaantalbinnen5km float, theatergemiddeldaantalbinnen10km float, theatergemiddeldaantalbinnen20km float, gemiddeldeafstandtotmuseum float, gemiddeldaantalmuseabinnen5km float, gemiddeldaantalmuseabinnen10km float, gemiddeldaantalmuseabinnen20km float, afstandtotopenbaargroentotaal float, afstandtotparkofplantsoen float, afstandtotdagrcreatiefterrein float, afstandtotbos float,
      afstandtotopennatuurterreintotaal float, afstandtotopendroognatuurterrein float, afstandtotopennatnatuurlijkterrein float, afstandtotsemiopenbaargroentotaal float, afstandtotsportterrein float, afstandtotvolkstuin float, afstandtotverblijfsrecreatiefterrein float, afstandtotrecreatiefbinnenwater float, afstandtotbegraafplaats float, jrstatcode text, jaar integer, fuuid text
    -> Clipper [CLIPPER]
    -> Clipper_2 [CLIPPER]
    -> Clipper_3 [CLIPPER]
    -> Clipper_4 [CLIPPER]
Clipper
    ADD_NODATA = YES
    BOUNDARY_CASES = INSIDE
    CLEANING_TOLERANCE_LOOKUP = AUTO
    CLIPPED_ATTR = _clipped
    CLIPPERS_FIRST = NO
    GENERATE_LIST = NO
    INVALID_PARTS_HANDLING = REJECT_WHOLE
    MISSING_M_MODE_LOOKUP = LINEAR
    MISSING_Z_MODE_LOOKUP = PLANAR
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    CLEANING_TOLERANCE = Automatic
    MISSING_M_MODE = Linear Interpolation
    MISSING_Z_MODE = Planar Interpolation
    INSIDE -> Dissolver_Possible_Areas
Clipper_2
    ADD_NODATA = YES
    BOUNDARY_CASES = INSIDE
    CLEANING_TOLERANCE_LOOKUP = AUTO
    CLIPPED_ATTR = _clipped
    CLIPPERS_FIRST = NO
    GENERATE_LIST = NO
    INVALID_PARTS_HANDLING = REJECT_WHOLE
    MISSING_M_MODE_LOOKUP = LINEAR
    MISSING_Z_MODE_LOOKUP = PLANAR
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    CLEANING_TOLERANCE = Automatic
    MISSING_M_MODE = Linear Interpolation
    MISSING_Z_MODE = Planar Interpolation
    INSIDE -> Dissolver_Possible_Areas
Clipper_3
    ADD_NODATA = YES
    BOUNDARY_CASES = INSIDE
    CLEANING_TOLERANCE_LOOKUP = AUTO
    CLIPPED_ATTR = _clipped
    CLIPPERS_FIRST = NO
    GENERATE_LIST = NO
    INVALID_PARTS_HANDLING = REJECT_WHOLE
    MISSING_M_MODE_LOOKUP = LINEAR
    MISSING_Z_MODE_LOOKUP = PLANAR
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    CLEANING_TOLERANCE = Automatic
    MISSING_M_MODE = Linear Interpolation
    MISSING_Z_MODE = Planar Interpolation
    INSIDE -> TestFilter_3
TestFilter_3
    DEFAULT_VALUE = <UNFILTERED>
    PASSED_TEST_GROUP_OUTPUT = FIRST
    TEST_LIST = "BOOL_OP,OR,COMPOSITE_TEST,""""""1"""""",TEST_CLAUSE,TEST @Value(plus_type) IN functioneel beheer: hondenuitlaatplaats,recreatie: park,recreatie: speeltuin,recreatie: sportterrein,recreatie: volkstuin,",Tree Possible
    Tree Possible -> Dissolver_Possible_Areas
Note: Possible Areas: / inrit = Driveway / entrance ramp / parkeervlak = Parking area / voetgangersgebied = Pedestrian zone / voetpad = Footpath / sidewalk / Impossible Areas: (+Buffer) / rijbaan_regionale_weg = Regional road carriageway (+Buffer = 7m) / overweg = Level crossing (+Buffer = 10m) / spoorbaan = Railway track (+Buffer = 10m) / OV_baan = Public transport lane (+Buffer = 3m) / voetpad_op_trap = Footpath on stairs (+Buffer = 3m) / fietspad = Bicycle path (+Buffer = 3m) / rijbaan_lokale_weg = Local road carriageway (+Buffer = 3m)
bgt_wegdeel__trafficarea (reader SPATIALITE_NATIVE_6)
    attributes: ogc_fid integer, gml_id text, creationdate varchar(10), lv_publicatiedatum varchar(19), relatievehoogteligging integer, inonderzoek integer, tijdstipregistratie varchar(23), namespace varchar(8), lokaalid varchar(38), bronhouder varchar(5), bgt_status varchar(8), plus_status varchar(10), function varchar(21), surfacematerial varchar(19), kruinlijnwegdeel text, wegdeeloptalud integer, plus_fysiekvoorkomenwegdeel varchar(17), plus_functiewegdeel varchar(15), eindregistratie varchar(19), terminationdate varchar(10)
    -> Clipper_4 [CANDIDATE]
Clipper_4
    ADD_NODATA = YES
    BOUNDARY_CASES = INSIDE
    CLEANING_TOLERANCE_LOOKUP = AUTO
    CLIPPED_ATTR = _clipped
    CLIPPERS_FIRST = NO
    GENERATE_LIST = NO
    INVALID_PARTS_HANDLING = REJECT_WHOLE
    MISSING_M_MODE_LOOKUP = LINEAR
    MISSING_Z_MODE_LOOKUP = PLANAR
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    CLEANING_TOLERANCE = Automatic
    MISSING_M_MODE = Linear Interpolation
    MISSING_Z_MODE = Planar Interpolation
    INSIDE -> TestFilter_4
TestFilter_4
    DEFAULT_VALUE = buffer
    PASSED_TEST_GROUP_OUTPUT = FIRST
    TEST_LIST = "BOOL_OP,OR,COMPOSITE_TEST,""""""1"""""",TEST_CLAUSE,TEST @Value(function) IN inrit,parkeervlak,voetgangersgebied,voetpad",green
    green -> Dissolver_Possible_Areas
Dissolver_Possible_Areas
    ACCUM_INPUT_ATTRS_LOOKUP = One
    CLEANING_TOLERANCE_LOOKUP = AUTO
    CONNECT_Z_MODE_LOOKUP = FIRST_WINS
    DEAGGREGATE_INPUT = Yes
    ACCUM_INPUT_ATTRS = Use Attributes From One Feature
    CLEANING_TOLERANCE = Automatic
    CONNECT_Z_MODE = First Wins
    AREA -> AttributeRemover_2
AttributeRemover_2
    REMOVE_ATTRS = ogc_fid,gml_id,creationdate,lv_publicatiedatum,relatievehoogteligging,inonderzoek,tijdstipregistratie,namespace,lokaalid,bronhouder,bgt_status,plus_status,function,surfacematerial,kruinlijnwegdeel,wegdeeloptalud,plus_fysiekvoorkomenwegdeel,plus_functiewegdeel,eindregistratie,terminationdate,_clipped,bgt_type,plus_type,naam,bgt_fysiekvoorkomen,onbegroeidterreindeeloptalud,plus_fysiekvoorkomen,kruinlijnonbegroeidterreindeel,class,begroeidterreindeeloptalud,kruinlijnbegroeidterreindeel
    -> AttributeCreator
AttributeCreator
    ATTR_TABLE = SET_TO potential (varchar(13)) = tree_possible
    -> Clipper_9 [CANDIDATE]
Note: Impossible Areas: (+Buffer = 3m) / pand = building/structure
building (reader SPATIALITE_NATIVE_7)
    attributes: ogc_fid integer, rowid integer, gml_id text, gml_parent_id text, citygml_target_uri text, citygml_feature_role text, citygml_feature_role_attr_name text, citygml_feature_role_attr_val text, gml_description text, gml_name text, citygml_creationdate text, citygml_terminationdate text, externalreference{}.externalobject.name text, externalreference{}.externalobject.uri text, externalreference{}.informationsystem text, citygml_generalizes_to{}.xlink_href text, citygml_relative_to_terrain text, citygml_relative_to_water text, citygml_appearance{}.xlink_href text, citygml_class text, citygml_class_codespace text, citygml_function{} text, citygml_function{}.codespace text, citygml_usage{} text, citygml_usage{}.codespace text, citygml_year_of_construction text, citygml_year_of_demolition text, citygml_roof_type text, citygml_roof_type_codespace text, citygml_measured_height float,
      citygml_measured_height_units text, citygml_storeys_above_ground text, citygml_storeys_below_ground text, citygml_storey_heights_above_ground text, citygml_storey_heights_above_ground_units text, citygml_storey_heights_below_ground text, citygml_storey_heights_below_ground_units text, citygml_outer_building_installation{}.xlink_href text, citygml_interior_building_installation{}.xlink_href text, citygml_bounded_by{}.xlink_href text, citygml_level_of_detail{} text, citygml_interior_room{}.xlink_href text, citygml_consists_of_building_part{}.xlink_href text, citygml_address{}.xlink_href text, type text, aantal_adressen text, aantal_bouwlagen text, buurt text, hoogste_bouwlaag text, laagste_bouwlaag text, pandsoort text, wijk text, ycd_tree text, yhd_tree text, gmlid text, footprint area text, ycd_proposed_tree text, yhd_proposed_tree text, ycd_diff float, yhd_diff float,
      diff float
    -> Bufferer
    -> Bufferer_5
    -> Bufferer_17
Bufferer_17
    ANGLE = 22.5
    CAP_STYLE_LOOKUP = CAP_PROJECTING
    CORNER_STYLE_LOOKUP = JOIN_ARC
    MODE = AREA
    OFFSET = 0.2
    OFFSET_UNITS = METERS
    PRECISION = APPROX
    CAP_STYLE = Square
    CORNER_STYLE = Arc
    BUFFERED -> Clipper_13 [CLIPPER]
    BUFFERED -> Clipper_14 [CLIPPER]
    BUFFERED -> Clipper_15 [CLIPPER]
    BUFFERED -> Clipper_16 [CLIPPER]
Bufferer_5
    ANGLE = 22.5
    CAP_STYLE_LOOKUP = CAP_PROJECTING
    CORNER_STYLE_LOOKUP = JOIN_ARC
    MODE = AREA
    OFFSET = 5
    OFFSET_UNITS = METERS
    PRECISION = APPROX
    CAP_STYLE = Square
    CORNER_STYLE = Arc
    BUFFERED -> Clipper_10 [CLIPPER]
Bufferer
    ANGLE = 22.5
    CAP_STYLE_LOOKUP = CAP_PROJECTING
    CORNER_STYLE_LOOKUP = JOIN_ARC
    MODE = AREA
    OFFSET = 3
    OFFSET_UNITS = METERS
    PRECISION = APPROX
    CAP_STYLE = Square
    CORNER_STYLE = Arc
    BUFFERED -> Dissolver_Impossible_Areas
Dissolver_Impossible_Areas
    ACCUM_INPUT_ATTRS_LOOKUP = One
    CLEANING_TOLERANCE_LOOKUP = AUTO
    CONNECT_Z_MODE_LOOKUP = FIRST_WINS
    DEAGGREGATE_INPUT = Yes
    ACCUM_INPUT_ATTRS = Use Attributes From One Feature
    CLEANING_TOLERANCE = Automatic
    CONNECT_Z_MODE = First Wins
    AREA -> AttributeRemover
AttributeRemover
    REMOVE_ATTRS = _clipped,bgt_status,bronhouder,class,creationdate,eindregistratie,function,gml_id,inonderzoek,lokaalid,lv_publicatiedatum,namespace,ogc_fid,plus_status,plus_type,relatievehoogteligging,terminationdate,tijdstipregistratie,kruinlijnwegdeel,plus_functiewegdeel,plus_fysiekvoorkomenwegdeel,surfacematerial,wegdeeloptalud
    -> AttributeCreator_2
AttributeCreator_2
    ATTR_TABLE = SET_TO potential (varchar(15)) = tree_impossible
    -> Clipper_9 [CLIPPER]
Clipper_9
    ADD_NODATA = YES
    BOUNDARY_CASES = INSIDE
    CLEANING_TOLERANCE_LOOKUP = AUTO
    CLIPPED_ATTR = _clipped
    CLIPPERS_FIRST = NO
    GENERATE_LIST = NO
    INVALID_PARTS_HANDLING = REJECT_WHOLE
    MISSING_M_MODE_LOOKUP = LINEAR
    MISSING_Z_MODE_LOOKUP = PLANAR
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    CLEANING_TOLERANCE = Automatic
    MISSING_M_MODE = Linear Interpolation
    MISSING_Z_MODE = Planar Interpolation
    OUTSIDE -> Clipper_10 [CANDIDATE]
    OUTSIDE -> Table1 (writer SPATIALITE_NATIVE_20)
    OUTSIDE -> Clipper_17 [CANDIDATE]
    OUTSIDE -> Clipper_18 [CANDIDATE]
Clipper_18
    ADD_NODATA = YES
    BOUNDARY_CASES = INSIDE
    CLEANING_TOLERANCE_LOOKUP = AUTO
    CLIPPED_ATTR = _clipped
    CLIPPERS_FIRST = NO
    GENERATE_LIST = NO
    INVALID_PARTS_HANDLING = REJECT_WHOLE
    MISSING_M_MODE_LOOKUP = LINEAR
    MISSING_Z_MODE_LOOKUP = PLANAR
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    CLEANING_TOLERANCE = Automatic
    MISSING_M_MODE = Linear Interpolation
    MISSING_Z_MODE = Planar Interpolation
    INSIDE -> Dissolver_2
Dissolver_2
    ACCUM_INPUT_ATTRS_LOOKUP = All
    CLEANING_TOLERANCE_LOOKUP = AUTO
    CONNECT_Z_MODE_LOOKUP = FIRST_WINS
    DEAGGREGATE_INPUT = Yes
    ACCUM_INPUT_ATTRS = Merge Incoming Attributes
    CLEANING_TOLERANCE = Automatic
    CONNECT_Z_MODE = First Wins
    AREA -> AreaCalculator
AreaCalculator
    AREA_ATTR = _area
    AREA_TYPE = Plane Area
    MULT = 1
    -> Aggregator
Aggregator
    ACCUM_ATTRS = None
    AGGREGATE_TYPE = Homogeneous Collection (If Possible)
    MODE = Geometry - Assemble One Level
    SEP = ,
    SUM = _area
Table1 (writer SPATIALITE_NATIVE_20)
    attributes: potential varchar(13), _clipped varchar(9)
Clipper_17
    ADD_NODATA = YES
    BOUNDARY_CASES = INSIDE
    CLEANING_TOLERANCE_LOOKUP = AUTO
    CLIPPED_ATTR = _clipped
    CLIPPERS_FIRST = NO
    GENERATE_LIST = NO
    INVALID_PARTS_HANDLING = REJECT_WHOLE
    MISSING_M_MODE_LOOKUP = LINEAR
    MISSING_Z_MODE_LOOKUP = PLANAR
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    CLEANING_TOLERANCE = Automatic
    MISSING_M_MODE = Linear Interpolation
    MISSING_Z_MODE = Planar Interpolation
    INSIDE -> Dissolver
Dissolver
    ACCUM_INPUT_ATTRS_LOOKUP = None
    CLEANING_TOLERANCE_LOOKUP = AUTO
    CONNECT_Z_MODE_LOOKUP = FIRST_WINS
    DEAGGREGATE_INPUT = Yes
    ACCUM_INPUT_ATTRS = Drop Incoming Attributes
    CLEANING_TOLERANCE = Automatic
    CONNECT_Z_MODE = First Wins
    AREA -> AreaCalculator_2
AreaCalculator_2
    AREA_ATTR = _area
    AREA_TYPE = Plane Area
    MULT = 1
    -> Aggregator_2
Aggregator_2
    ACCUM_ATTRS = None
    AGGREGATE_TYPE = Homogeneous Collection (If Possible)
    MODE = Geometry - Assemble One Level
    SEP = ,
    SUM = _area
Clipper_10
    ADD_NODATA = YES
    BOUNDARY_CASES = INSIDE
    CLEANING_TOLERANCE_LOOKUP = AUTO
    CLIPPED_ATTR = _clipped
    CLIPPERS_FIRST = NO
    GENERATE_LIST = NO
    INVALID_PARTS_HANDLING = REJECT_WHOLE
    MISSING_M_MODE_LOOKUP = LINEAR
    MISSING_Z_MODE_LOOKUP = PLANAR
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    CLEANING_TOLERANCE = Automatic
    MISSING_M_MODE = Linear Interpolation
    MISSING_Z_MODE = Planar Interpolation
    INSIDE -> Clipper_11 [CLIPPER]
    INSIDE -> Clipper_12 [CLIPPER]
Clipper_11
    ADD_NODATA = YES
    BOUNDARY_CASES = INSIDE
    CLEANING_TOLERANCE_LOOKUP = AUTO
    CLIPPED_ATTR = _clipped
    CLIPPERS_FIRST = NO
    GENERATE_LIST = NO
    INVALID_PARTS_HANDLING = REJECT_WHOLE
    MISSING_M_MODE_LOOKUP = LINEAR
    MISSING_Z_MODE_LOOKUP = PLANAR
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    CLEANING_TOLERANCE = Automatic
    MISSING_M_MODE = Linear Interpolation
    MISSING_Z_MODE = Planar Interpolation
    INSIDE -> Counter
Counter
    CNT_ATTR = _count
    DOMAIN = counter
    SCOPE = Global
    START = 0
    -> AttributeManager_5
AttributeManager_5
    ATTR_TABLE:
      REMOVE _part_number (uint64)
      REMOVE _geometry_label (buffer)
      REMOVE _column (uint32)
      REMOVE _row (uint32)
      REMOVE ogc_fid (int64)
      REMOVE _clipped (char(3))
      SET_TO id (varchar(200)) = pt_@Value(_count)_kvz
    -> AttributeManager_4
AttributeManager_4
    ATTR_TABLE = REMOVE _count (int64)
    -> Bufferer_16
    -> Bufferer_18
Bufferer_16
    ANGLE = 30
    CAP_STYLE_LOOKUP = CAP_ROUND
    CORNER_STYLE_LOOKUP = JOIN_ROUND
    MODE = AREA
    OFFSET = 1.5
    OFFSET_UNITS = NONE
    PRECISION = APPROX
    CAP_STYLE = Round
    CORNER_STYLE = Round
    BUFFERED -> Clipper_13 [CANDIDATE]
Clipper_13
    ADD_NODATA = YES
    BOUNDARY_CASES = INSIDE
    CLEANING_TOLERANCE_LOOKUP = AUTO
    CLIPPED_ATTR = _clipped
    CLIPPERS_FIRST = NO
    GENERATE_LIST = NO
    INVALID_PARTS_HANDLING = REJECT_WHOLE
    MISSING_M_MODE_LOOKUP = LINEAR
    MISSING_Z_MODE_LOOKUP = PLANAR
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    CLEANING_TOLERANCE = Automatic
    MISSING_M_MODE = Linear Interpolation
    MISSING_Z_MODE = Planar Interpolation
    OUTSIDE -> 3DForcer_2
3DForcer_2
    KEEPZVAL = No
    ZVALATTR = @Value(_inside_z)
    -> AttributeManager_8
AttributeManager_8
    ATTR_TABLE:
      RENAME_SET_VALUE _inside_z > _zmin (real64)
      RENAME_SET_VALUE _roof_z > _zmax (real32)
      RENAME_SET_VALUE id > gml_id (varchar(200))
      REMOVE _clipped (char(9))
    -> Table1 (writer SPATIALITE_NATIVE_9)
Table1 (writer SPATIALITE_NATIVE_9)
    attributes: _zmin double, _zmax float, gml_id varchar(200)
Bufferer_18
    ANGLE = 30
    CAP_STYLE_LOOKUP = CAP_ROUND
    CORNER_STYLE_LOOKUP = JOIN_ROUND
    MODE = AREA
    OFFSET = 0.75
    OFFSET_UNITS = NONE
    PRECISION = APPROX
    CAP_STYLE = Round
    CORNER_STYLE = Round
    BUFFERED -> Clipper_15 [CANDIDATE]
Clipper_15
    ADD_NODATA = YES
    BOUNDARY_CASES = INSIDE
    CLEANING_TOLERANCE_LOOKUP = AUTO
    CLIPPED_ATTR = _clipped
    CLIPPERS_FIRST = NO
    GENERATE_LIST = NO
    INVALID_PARTS_HANDLING = REJECT_WHOLE
    MISSING_M_MODE_LOOKUP = LINEAR
    MISSING_Z_MODE_LOOKUP = PLANAR
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    CLEANING_TOLERANCE = Automatic
    MISSING_M_MODE = Linear Interpolation
    MISSING_Z_MODE = Planar Interpolation
    OUTSIDE -> 3DForcer_3
3DForcer_3
    KEEPZVAL = No
    ZVALATTR = @Value(_inside_z)
    -> AttributeManager_9
AttributeManager_9
    ATTR_TABLE:
      RENAME_SET_VALUE _inside_z > _zmin (real64)
      RENAME_SET_VALUE _roof_z > _zmax (real32)
      RENAME_SET_VALUE id > gml_id (varchar(200))
      REMOVE _clipped (char(9))
    -> Table1 (writer SPATIALITE_NATIVE_18)
Table1 (writer SPATIALITE_NATIVE_18)
    attributes: _zmin double, _zmax float, gml_id varchar(200)
Clipper_12
    ADD_NODATA = YES
    BOUNDARY_CASES = INSIDE
    CLEANING_TOLERANCE_LOOKUP = AUTO
    CLIPPED_ATTR = _clipped
    CLIPPERS_FIRST = NO
    GENERATE_LIST = NO
    INVALID_PARTS_HANDLING = REJECT_WHOLE
    MISSING_M_MODE_LOOKUP = LINEAR
    MISSING_Z_MODE_LOOKUP = PLANAR
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    CLEANING_TOLERANCE = Automatic
    MISSING_M_MODE = Linear Interpolation
    MISSING_Z_MODE = Planar Interpolation
    INSIDE -> Counter_2
Counter_2
    CNT_ATTR = _count
    DOMAIN = counter
    SCOPE = Global
    START = 0
    -> AttributeManager_3
AttributeManager_3
    ATTR_TABLE:
      REMOVE _part_number (uint64)
      REMOVE _geometry_label (buffer)
      REMOVE _column (uint32)
      REMOVE _row (uint32)
      REMOVE ogc_fid (int64)
      REMOVE _clipped (char(3))
      SET_TO id (varchar(200)) = pt_@Value(_count)_afr
    -> AttributeManager_6
AttributeManager_6
    ATTR_TABLE = REMOVE _count (int64)
    -> Bufferer_6
    -> Bufferer_19
Bufferer_6
    ANGLE = 30
    CAP_STYLE_LOOKUP = CAP_ROUND
    CORNER_STYLE_LOOKUP = JOIN_ROUND
    MODE = AREA
    OFFSET = 1.5
    OFFSET_UNITS = NONE
    PRECISION = APPROX
    CAP_STYLE = Round
    CORNER_STYLE = Round
    BUFFERED -> Clipper_14 [CANDIDATE]
Clipper_14
    ADD_NODATA = YES
    BOUNDARY_CASES = INSIDE
    CLEANING_TOLERANCE_LOOKUP = AUTO
    CLIPPED_ATTR = _clipped
    CLIPPERS_FIRST = NO
    GENERATE_LIST = NO
    INVALID_PARTS_HANDLING = REJECT_WHOLE
    MISSING_M_MODE_LOOKUP = LINEAR
    MISSING_Z_MODE_LOOKUP = PLANAR
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    CLEANING_TOLERANCE = Automatic
    MISSING_M_MODE = Linear Interpolation
    MISSING_Z_MODE = Planar Interpolation
    OUTSIDE -> 3DForcer
3DForcer
    KEEPZVAL = No
    ZVALATTR = @Value(_inside_z)
    -> AttributeManager_7
AttributeManager_7
    ATTR_TABLE:
      RENAME_SET_VALUE _inside_z > _zmin (real64)
      RENAME_SET_VALUE _roof_z > _zmax (real32)
      RENAME_SET_VALUE id > gml_id (varchar(200))
      REMOVE _clipped (char(9))
    -> Table1 (writer SPATIALITE_NATIVE_17)
Table1 (writer SPATIALITE_NATIVE_17)
    attributes: _zmin double, _zmax float, gml_id varchar(200)
Bufferer_19
    ANGLE = 30
    CAP_STYLE_LOOKUP = CAP_ROUND
    CORNER_STYLE_LOOKUP = JOIN_ROUND
    MODE = AREA
    OFFSET = 0.75
    OFFSET_UNITS = NONE
    PRECISION = APPROX
    CAP_STYLE = Round
    CORNER_STYLE = Round
    BUFFERED -> Clipper_16 [CANDIDATE]
Clipper_16
    ADD_NODATA = YES
    BOUNDARY_CASES = INSIDE
    CLEANING_TOLERANCE_LOOKUP = AUTO
    CLIPPED_ATTR = _clipped
    CLIPPERS_FIRST = NO
    GENERATE_LIST = NO
    INVALID_PARTS_HANDLING = REJECT_WHOLE
    MISSING_M_MODE_LOOKUP = LINEAR
    MISSING_Z_MODE_LOOKUP = PLANAR
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    CLEANING_TOLERANCE = Automatic
    MISSING_M_MODE = Linear Interpolation
    MISSING_Z_MODE = Planar Interpolation
    OUTSIDE -> 3DForcer_4
3DForcer_4
    KEEPZVAL = No
    ZVALATTR = @Value(_inside_z)
    -> AttributeManager_10
AttributeManager_10
    ATTR_TABLE:
      RENAME_SET_VALUE _inside_z > _zmin (real64)
      RENAME_SET_VALUE _roof_z > _zmax (real32)
      RENAME_SET_VALUE id > gml_id (varchar(200))
      REMOVE _clipped (char(9))
    -> Table1 (writer SPATIALITE_NATIVE_19)
Table1 (writer SPATIALITE_NATIVE_19)
    attributes: _zmin double, _zmax float, gml_id varchar(200)
