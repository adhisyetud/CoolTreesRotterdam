FME workspace 2_sqltree_to_modeltree_perbuurt_new_final.fmw

Parameters:
- DestDataset_CITYGML = C:\MSc\Q2_2\Cooling_Rotterdam\Start_3\03_Intermediate_Results\2Buurt\CT\W\Cyllinder_CT_Afr_Winter_New4.gml   # Destination CityGML Document
- SourceDataset_SPATIALITE_NATIVE_4 = C:\MSc\Q2_2\Cooling_Rotterdam\Start_3\03_Intermediate_Results\2Buurt\CT\W\Round_CT_Afr_Winter.sqlite   # SpatiaLite Database
- SourceDataset_SPATIALITE_NATIVE = C:\MSc\Q2_2\Cooling_Rotterdam\Start_3\01_Input\2Buurt\Afrikaanderwijk_Building.sqlite   # SpatiaLite Database

Readers:
- SPATIALITE_NATIVE_1: SPATIALITE_NATIVE from $(SourceDataset_SPATIALITE_NATIVE)
- SPATIALITE_NATIVE_3: SPATIALITE_NATIVE from $(SourceDataset_SPATIALITE_NATIVE_4)

Writers:
- CITYGML_1: CITYGML to $(DestDataset_CITYGML) in EPSG:28992

building (reader SPATIALITE_NATIVE_1)
    attributes: ogc_fid integer
    -> Bufferer
Bufferer
    ANGLE = 30
    CAP_STYLE_LOOKUP = CAP_PROJECTING
    CORNER_STYLE_LOOKUP = JOIN_ARC
    MODE = AREA
    OFFSET = 1
    OFFSET_UNITS = METERS
    PRECISION = APPROX
    CAP_STYLE = Square
    CORNER_STYLE = Arc
    BUFFERED -> Clipper [CLIPPER]
Table1 (reader SPATIALITE_NATIVE_3)
    attributes: gml_id text, gml_parent_id text, citygml_target_uri text, citygml_feature_role text, citygml_feature_role_attr_name text, citygml_feature_role_attr_val text, gml_description text, gml_name text, citygml_creationDate text, citygml_terminationDate text, externalReference{}.externalObject.name text, externalReference{}.externalObject.uri text, externalReference{}.informationSystem text, citygml_generalizes_to{}.xlink_href text, citygml_relative_to_terrain varchar(33), citygml_relative_to_water varchar(38), citygml_class text, citygml_class_codeSpace text, citygml_function{} text, citygml_function{}.codeSpace text, citygml_usage{} text, citygml_usage{}.codeSpace text, citygml_species text, citygml_species_codeSpace text, citygml_height double, citygml_height_units text, citygml_trunk_diameter double, citygml_trunk_diameter_units text, citygml_crown_diameter double, citygml_crown_diameter_units text,
      citygml_level_of_detail{} text, Aanlegjaar text, Beheerobjectomschrijving text, Boom_id text, Boomsortiment text, Boomsortiment_nederlands text, Boomstatus text, Brondatum text, Buurt text, Geslacht text, Hoogte text, Laatste_mutatie text, Ontwikkeling text, Stamdiameter text, Stamlengte text, Straat text, Thema text, Wijk text, tree_part text, _clipped varchar(3), Type text, _xmin double, _xmax double, _ymin double, _ymax double, _zmin double, _zmax double
    -> Clipper [CANDIDATE]
Clipper
    ADD_NODATA = YES
    BOUNDARY_CASES = INSIDE
    CLEANING_TOLERANCE_LOOKUP = AUTO
    CLIPPED_ATTR = _clipped
    CLIPPERS_FIRST = NO
    GENERATE_LIST = NO
    INVALID_PARTS_HANDLING = REJECT_WHOLE
    MISSING_M_MODE_LOOKUP = LINEAR
    MISSING_Z_MODE_LOOKUP = PLANAR
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    CLEANING_TOLERANCE = Automatic
    MISSING_M_MODE = Linear Interpolation
    MISSING_Z_MODE = Planar Interpolation
    OUTSIDE -> AttributeManager_3
AttributeManager_3
    ATTR_TABLE:
      SET_TO name (varchar(17)) = Trees_Building
      SET_TO class (varchar(8)) = Building
      SET_TO function (uint16) = 1010
      SET_TO usage (varchar(11)) = Residential
      SET_TO storeys_ab (uint8) = 5
      SET_TO storeys_be (uint8) = 0
      SET_TO constr_y (uint16) = 1930
      SET_TO ga_people (uint8) = 5
      SET_TO ground_z (uint8) = @Value(_zmin)
      SET_TO roof_z (uint8) = @Value(_zmax)
      SET_TO is_part (uint8) = 0
      REMOVE gml_parent_id (buffer)
      REMOVE citygml_target_uri (buffer)
      REMOVE citygml_feature_role (buffer)
      REMOVE citygml_feature_role_attr_name (buffer)
      REMOVE citygml_feature_role_attr_val (buffer)
      REMOVE gml_description (buffer)
      REMOVE gml_name (buffer)
      REMOVE citygml_creationDate (buffer)
      REMOVE citygml_terminationDate (buffer)
      REMOVE externalReference{}.externalObject.name (buffer)
      REMOVE externalReference{}.externalObject.uri (buffer)
      REMOVE externalReference{}.informationSystem (buffer)
      REMOVE citygml_generalizes_to{}.xlink_href (buffer)
      REMOVE citygml_relative_to_terrain (varchar(33))
      REMOVE citygml_relative_to_water (varchar(38))
      REMOVE citygml_class (buffer)
      REMOVE citygml_class_codeSpace (buffer)
      REMOVE citygml_function{} (buffer)
      REMOVE citygml_function{}.codeSpace (buffer)
      REMOVE citygml_usage{} (buffer)
      REMOVE citygml_usage{}.codeSpace (buffer)
      REMOVE citygml_species (buffer)
      REMOVE citygml_species_codeSpace (buffer)
      REMOVE citygml_height (real64)
      REMOVE citygml_height_units (buffer)
      REMOVE citygml_trunk_diameter (real64)
      REMOVE citygml_trunk_diameter_units (buffer)
      REMOVE citygml_crown_diameter (real64)
      REMOVE citygml_crown_diameter_units (buffer)
      REMOVE citygml_level_of_detail{} (buffer)
      REMOVE Aanlegjaar (buffer)
      REMOVE Beheerobjectomschrijving (buffer)
      REMOVE Boom_id (buffer)
      REMOVE Boomsortiment (buffer)
      REMOVE Boomsortiment_nederlands (buffer)
      REMOVE Boomstatus (buffer)
      REMOVE Brondatum (buffer)
      REMOVE Buurt (buffer)
      REMOVE Geslacht (buffer)
      REMOVE Hoogte (buffer)
      REMOVE Laatste_mutatie (buffer)
      REMOVE Ontwikkeling (buffer)
      REMOVE Stamdiameter (buffer)
      REMOVE Stamlengte (buffer)
      REMOVE Straat (buffer)
      REMOVE Thema (buffer)
      REMOVE Wijk (buffer)
      REMOVE tree_part (buffer)
      REMOVE Type (buffer)
      REMOVE _xmin (real64)
      REMOVE _xmax (real64)
      REMOVE _ymin (real64)
      REMOVE _ymax (real64)
      SET_TO _offset_roof (varchar(200)) = @sub(@Value(_zmax),@Value(_zmin))
    -> AttributeManager_4
AttributeManager_4
    ATTR_TABLE = SET_TO storeys_ab (uint8) = @round(@div(@Value(_offset_roof),3),0)
    -> AttributeManager_2
    -> buildings
    -> AttributeKeeper
Note: You may have to adjust the path to the input and output files / Open the readers/writers on the left (Navigator) and adapt the path accordingly
buildings: Inspector
AttributeManager_2
    ATTR_TABLE:
      RENAME_SET_VALUE name > gml_name (varchar(17))
      RENAME_SET_VALUE class > citygml_class (varchar(11))
      RENAME_SET_VALUE storeys_ab > citygml_storeys_above_ground (uint8)
      RENAME_SET_VALUE storeys_be > citygml_storeys_below_ground (uint8)
      RENAME_SET_VALUE constr_y > citygml_year_of_construction (uint16)
      RENAME_SET_VALUE ga_people > numberResidents (uint8)
    -> AttributeSplitter
GeometryRemover
    REMOVE_COORDSYS = No
    -> Aggregator_2
Extruder
    DIRECTION_LOOKUP = AUTO
    DISTANCE = @Value(_offset_roof)
    DIRECTION = Auto
    EXTRUDED -> GeometryCoercer
GeometryCoercer
    GQUERY:
      for $geom in //geometry
      where $geom/count(parent::geometry) = 0
      return number($geom/@fme_id)
    KIND = fme_composite_surface
    COERCED -> GeometryCoercer_2
GeometryCoercer_2
    GQUERY:
      for $geom in //geometry
      where $geom/count(parent::geometry) = 0
      return number($geom/@fme_id)
    KIND = fme_brep_solid
    COERCED -> AttributeCreator_3
AttributeCreator_3
    ATTR_TABLE:
      SET_TO gml_id (varchar(200)) = Solid_UUID_@UUID()
      SET_TO citygml_lod_name (varchar(9)) = lod1Solid
    -> GeometryPropertySetter_2
GeometryPropertySetter_2
    DO_REMOVE_ATTR = *
    GQUERY:
      for $geom in //geometry
      where $geom/@fme_geometry_type = 'IFMEBRepSolid'
      return number($geom/@fme_id)
    OVERWRITE_CHOICE_OPT = yes
    SETTYPE_PARAM = Traits From Attributes
    SRC_ATTRS = citygml_lod_name gml_id
    OVERWRITE_CHOICE = Yes
    REMOVE_ATTRIBUTE = Yes
    SET -> AttributeKeeper_3
AttributeKeeper_3
    CREATE_BULK_MODE_FEATURES = NO
    KEEP_ATTRS = gml_id_building
    -> AttributeRenamer_3
AttributeRenamer_3
    ATTR_TABLE = RENAME_SET_DEFAULT gml_id_building > gml_id
    KEEP_RENAMED_ONLY = no
    MISSING_INPUT_ATTRS = REMOVE
    -> Aggregator_2
Aggregator_2
    ACCUM_ATTRS = All
    AGGREGATE_TYPE = Homogeneous Collection (If Possible)
    GROUP_BY = gml_id
    MODE = Geometry - Assemble One Level
    SEP = ,
    ACCUM_ATTRS_NAME = Merge Incoming Attributes
    AGGREGATE -> Building (writer CITYGML_1)
Creator
    GEOMTYPE = Geometry Object
    NUM = 1
    CREATED -> AttributeManager
AttributeManager
    ATTR_TABLE:
      SET_TO gml_name (varchar(5)) = Trees
      SET_TO gml_description (varchar(5)) = Trees
    -> CityModel (writer CITYGML_1)

Bookmark: Attribute_mapping
AttributeSplitter
    ATTR_NAME = function
    DELIMITER = ;
    DROP_EMPTY_PARTS = NO
    LIST_NAME = citygml_function
    TRIM_TYPE = BOTH
    -> AttributeSplitter_2
AttributeSplitter_2
    ATTR_NAME = usage
    DELIMITER = ;
    DROP_EMPTY_PARTS = NO
    LIST_NAME = citygml_usage
    TRIM_TYPE = BOTH
    -> AttributeRemover
AttributeRemover
    REMOVE_ATTRS = function,usage
    -> GeometryRemover

Bookmark: Roof offset
AttributeKeeper
    CREATE_BULK_MODE_FEATURES = NO
    KEEP_ATTRS = is_part,_offset_roof,gml_id,_zmin,ground_z
    -> AttributeRenamer
AttributeRenamer
    ATTR_TABLE = RENAME_SET_DEFAULT gml_id > gml_id_building
    KEEP_RENAMED_ONLY = no
    MISSING_INPUT_ATTRS = PRESERVE
    -> Offsetter

Bookmark: New Bookmark
Offsetter
    MODE_LOOKUP = CARTESIAN
    XOFF = 0
    YOFF = 0
    ZOFF = 0
    MODE = Cartesian Coordinate
    OFFSET -> Orientor
    OFFSET -> Extruder

Bookmark: Create multisurface
Orientor
    FLIP_APPEARANCES_LOOKUP = FLIP_APPEARANCES
    KIND = REVERSE
    FLIP_APPEARANCES_CHOICE = Yes
    ORIENTED -> FaceReplacer
FaceReplacer
    ANGULAR_TOLERANCE_CHOICE_LOOKUP = AUTO
    THICKNESS_TOLERANCE_CHOICE_LOOKUP = AUTO
    ANGULAR_TOLERANCE_CHOICE = Automatic
    THICKNESS_TOLERANCE_CHOICE = Automatic
    -> Aggregator
Aggregator
    ACCUM_ATTRS = One
    AGGREGATE_TYPE = Homogeneous Collection (If Possible)
    GROUP_BY = gml_id_building
    MODE = Geometry - Assemble One Level
    SEP = ,
    ACCUM_ATTRS_NAME = Use Attributes From One Feature
    AGGREGATE -> AttributeCreator

Bookmark: Create citygml id and lod0footprint attributes
AttributeCreator
    ATTR_TABLE:
      SET_TO gml_id (varchar(200)) = MultiSurf_UUID_@UUID()
      SET_TO citygml_lod_name (varchar(200)) = lod0FootPrint
    -> GeometryPropertySetter
GeometryPropertySetter
    DO_REMOVE_ATTR = *
    GQUERY:
      for $geom in //geometry
      where $geom/@fme_geometry_type = 'IFMEMultiSurface'
      return number($geom/@fme_id)
    OVERWRITE_CHOICE_OPT = yes
    SETTYPE_PARAM = Traits From Attributes
    SRC_ATTRS = citygml_lod_name gml_id
    OVERWRITE_CHOICE = Yes
    REMOVE_ATTRIBUTE = Yes
    SET -> AttributeKeeper_2

Bookmark: Lod0 attributes rename and remove geometry
AttributeKeeper_2
    CREATE_BULK_MODE_FEATURES = NO
    KEEP_ATTRS = gml_id_building
    -> AttributeRenamer_2
AttributeRenamer_2
    ATTR_TABLE = RENAME_SET_DEFAULT gml_id_building > gml_id
    KEEP_RENAMED_ONLY = no
    MISSING_INPUT_ATTRS = REMOVE
    -> Aggregator_2

Bookmark: New Bookmark
Building (writer CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_class xml_buffer, citygml_class_codeSpace xml_buffer, citygml_function{} xml_buffer, citygml_function{}.codeSpace xml_buffer, citygml_usage{} xml_buffer, citygml_usage{}.codeSpace xml_buffer, citygml_year_of_construction xml_buffer, citygml_year_of_demolition xml_buffer, citygml_roof_type xml_buffer, citygml_roof_type_codeSpace xml_buffer, citygml_measured_height xml_real64, citygml_measured_height_units xml_buffer, citygml_storeys_above_ground xml_uint64, citygml_storeys_below_ground xml_uint64, citygml_storey_heights_above_ground xml_buffer,
      citygml_storey_heights_above_ground_units xml_buffer, citygml_storey_heights_below_ground xml_buffer, citygml_storey_heights_below_ground_units xml_buffer, citygml_outer_building_installation{}.xlink_href xml_buffer, citygml_interior_building_installation{}.xlink_href xml_buffer, citygml_bounded_by{}.xlink_href xml_buffer, citygml_level_of_detail{} xml_buffer, citygml_interior_room{}.xlink_href xml_buffer, citygml_consists_of_building_part{}.xlink_href xml_buffer, citygml_address{}.xlink_href xml_buffer, buildingColour xml_buffer, numberResidents xml_int32
BuildingPart (writer CITYGML_1)
    attributes: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

Bookmark: Write CityGML
CityModel (writer CITYGML_1)
    attributes: citygml_target_uri xml_buffer, gml_description xml_buffer, gml_name xml_buffer, citygml_city_object_member{}.xlink_href xml_buffer, citygml_appearance_member{}.xlink_href xml_buffer, gml_feature_member{}.xlink_href xml_buffer
CityObjectGroup (writer CITYGML_1)
    attributes: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
