FME workspace 3_modeltree_join_building_final.fmw

Parameters:
- SourceDataset_GML = C:\MSc\Q2_2\Cooling_Rotterdam\Start_3\01_Input\citygml_rotterdam_clean_fixed\Afrikaanderwijk_buildings_cl_fi.gml   # Source Geography Markup Language (GML) File(s)
- DestDataset_CITYGML = C:\MSc\Q2_2\Cooling_Rotterdam\Start_3\03_Intermediate_Results\2Buurt\CT\S\Model_CT_Afr_Summer.gml   # Destination CityGML Document
- SourceDataset_CITYGML = C:\MSc\Q2_2\Cooling_Rotterdam\Start_3\01_Input\citygml_rotterdam_clean_fixed\Afrikaanderwijk_buildings_cl_fi.gml   # Source CityGML File(s)
- DestDataset_CITYGML_2 = C:\MSc\Q2_2\Cooling_Rotterdam\Start_3\03_Intermediate_Results\2Buurt\CT\S\Model_CT_Afr_Summer.gml   # Destination CityGML Document
- SourceDataset_OGCGEOPACKAGE = C:\MSc\Q2_2\Cooling_Rotterdam\Start_3\01_Input\Feijenoord_All_bag_pand_ok_5.gpkg   # GeoPackage File
- SourceDataset_CITYGML_3 = C:\MSc\Q2_2\Cooling_Rotterdam\Start_3\03_Intermediate_Results\2Buurt\CT\S\Cyllinder_CT_Afr_Summer.gml   # Source CityGML File(s)

Readers:
- GML_1: GML from $(SourceDataset_GML)
- CITYGML_2: CITYGML from $(SourceDataset_CITYGML)
- OGCGEOPACKAGE_1: OGCGEOPACKAGE from $(SourceDataset_OGCGEOPACKAGE)
- CITYGML_4: CITYGML from $(SourceDataset_CITYGML_3)

Writers:
- CITYGML_1: CITYGML to $(DestDataset_CITYGML)
- CITYGML_3: CITYGML to $(DestDataset_CITYGML_2)

GenericAttribute (reader CITYGML_2)
    attributes: citygml_target_uri xml_buffer, name xml_buffer, value xml_buffer, type xml_buffer, units xml_buffer, AANTAL_ADRESSEN xml_buffer, AANTAL_BOUWLAGEN xml_buffer, BEGINGELDIGHEID xml_buffer, BUURT xml_buffer, GEBOUWNUMMER xml_buffer, HOOGSTE_BOUWLAAG xml_buffer, LAAGSTE_BOUWLAAG xml_buffer, PANDSOORT xml_buffer, WIJK xml_buffer
    -> Reprojector_8
Reprojector_8
    DEST = EPSG:28992
    INTERPOLATION_TYPE = ,NearestNeighbor
    RASTER_CELL_SIZE_LOOKUP = ,PreserveCells
    RASTER_TOLERANCE = 0.0
    INTERPOLATION_TYPE_NAME = Nearest Neighbor
    RASTER_CELL_SIZE = Preserve Cells
    REPROJECTED -> GenericAttribute (writer CITYGML_3)
GenericAttribute (writer CITYGML_3)
    attributes: citygml_target_uri xml_buffer, name xml_buffer, value xml_buffer, type xml_buffer, units xml_buffer, AANTAL_ADRESSEN xml_buffer, AANTAL_BOUWLAGEN xml_buffer, BEGINGELDIGHEID xml_buffer, BUURT xml_buffer, GEBOUWNUMMER xml_buffer, HOOGSTE_BOUWLAAG xml_buffer, LAAGSTE_BOUWLAAG xml_buffer, PANDSOORT xml_buffer, WIJK xml_buffer
OuterFloorSurface (reader CITYGML_2)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_level_of_detail{} xml_buffer, citygml_opening{}.xlink_href xml_buffer, type xml_buffer
    -> Reprojector_11
Reprojector_11
    DEST = EPSG:28992
    INTERPOLATION_TYPE = ,NearestNeighbor
    RASTER_CELL_SIZE_LOOKUP = ,PreserveCells
    RASTER_TOLERANCE = 0.0
    INTERPOLATION_TYPE_NAME = Nearest Neighbor
    RASTER_CELL_SIZE = Preserve Cells
    REPROJECTED -> OuterFloorSurface (writer CITYGML_3)
OuterFloorSurface (writer CITYGML_3)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_level_of_detail{} xml_buffer, citygml_opening{}.xlink_href xml_buffer, type xml_buffer
ParameterizedTexture (reader CITYGML_2)
    attributes: citygml_target_uri xml_buffer, citygml_feature_role xml_buffer, citygml_feature_role_attr_name xml_buffer, citygml_feature_role_attr_val xml_buffer, gml_description xml_buffer, gml_name xml_buffer, citygml_mime_type_codeSpace xml_buffer, type xml_buffer
    -> Reprojector_12
Reprojector_12
    DEST = EPSG:28992
    INTERPOLATION_TYPE = ,NearestNeighbor
    RASTER_CELL_SIZE_LOOKUP = ,PreserveCells
    RASTER_TOLERANCE = 0.0
    INTERPOLATION_TYPE_NAME = Nearest Neighbor
    RASTER_CELL_SIZE = Preserve Cells
    REPROJECTED -> ParameterizedTexture (writer CITYGML_3)
ParameterizedTexture (writer CITYGML_3)
    attributes: citygml_target_uri xml_buffer, citygml_feature_role xml_buffer, citygml_feature_role_attr_name xml_buffer, citygml_feature_role_attr_val xml_buffer, gml_description xml_buffer, gml_name xml_buffer, citygml_mime_type_codeSpace xml_buffer, type xml_buffer
RoofSurface (reader CITYGML_2)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_level_of_detail{} xml_buffer, citygml_opening{}.xlink_href xml_buffer, type xml_buffer
    -> Reprojector_13
Reprojector_13
    DEST = EPSG:28992
    INTERPOLATION_TYPE = ,NearestNeighbor
    RASTER_CELL_SIZE_LOOKUP = ,PreserveCells
    RASTER_TOLERANCE = 0.0
    INTERPOLATION_TYPE_NAME = Nearest Neighbor
    RASTER_CELL_SIZE = Preserve Cells
    REPROJECTED -> RoofSurface (writer CITYGML_3)
RoofSurface (writer CITYGML_3)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_level_of_detail{} xml_buffer, citygml_opening{}.xlink_href xml_buffer, type xml_buffer
WallSurface (reader CITYGML_2)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_level_of_detail{} xml_buffer, citygml_opening{}.xlink_href xml_buffer, type xml_buffer
    -> Reprojector_14
Reprojector_14
    DEST = EPSG:28992
    INTERPOLATION_TYPE = ,NearestNeighbor
    RASTER_CELL_SIZE_LOOKUP = ,PreserveCells
    RASTER_TOLERANCE = 0.0
    INTERPOLATION_TYPE_NAME = Nearest Neighbor
    RASTER_CELL_SIZE = Preserve Cells
    REPROJECTED -> WallSurface (writer CITYGML_3)
WallSurface (writer CITYGML_3)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_level_of_detail{} xml_buffer, citygml_opening{}.xlink_href xml_buffer, type xml_buffer
Building (reader CITYGML_2)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_class xml_buffer, citygml_class_codeSpace xml_buffer, citygml_function{} xml_buffer, citygml_function{}.codeSpace xml_buffer, citygml_usage{} xml_buffer, citygml_usage{}.codeSpace xml_buffer, citygml_year_of_construction xml_buffer, citygml_year_of_demolition xml_buffer, citygml_roof_type xml_buffer, citygml_roof_type_codeSpace xml_buffer, citygml_measured_height xml_real64, citygml_measured_height_units xml_buffer, citygml_storeys_above_ground xml_uint64, citygml_storeys_below_ground xml_uint64, citygml_storey_heights_above_ground xml_buffer,
      citygml_storey_heights_above_ground_units xml_buffer, citygml_storey_heights_below_ground xml_buffer, citygml_storey_heights_below_ground_units xml_buffer, citygml_outer_building_installation{}.xlink_href xml_buffer, citygml_interior_building_installation{}.xlink_href xml_buffer, citygml_bounded_by{}.xlink_href xml_buffer, citygml_level_of_detail{} xml_buffer, citygml_interior_room{}.xlink_href xml_buffer, citygml_consists_of_building_part{}.xlink_href xml_buffer, citygml_address{}.xlink_href xml_buffer, AANTAL_ADRESSEN xml_buffer, AANTAL_BOUWLAGEN xml_buffer, BEGINGELDIGHEID xml_buffer, BUURT xml_buffer, GEBOUWNUMMER xml_buffer, HOOGSTE_BOUWLAAG xml_buffer, LAAGSTE_BOUWLAAG xml_buffer, PANDSOORT xml_buffer, WIJK xml_buffer, type xml_buffer
    -> FeatureMerger [REQUESTOR]
Table1 (reader OGCGEOPACKAGE_1)
    attributes: feature_id int, rdf_seealso text, identificatie text, bouwjaar int, status text, gebruiksdoel text, oppervlakte_min int, oppervlakte_max int, aantal_verblijfsobjecten int, function text, fid int,PrimaryKey
    -> AttributeKeeper_2
AttributeKeeper_2
    CREATE_BULK_MODE_FEATURES = NO
    KEEP_ATTRS = function,identificatie
    -> gml_id_creator
gml_id_creator: AttributeCreator
    ATTR_TABLE = SET_TO gml_id (buffer) = BAG_@Value(identificatie)
    -> FeatureMerger [SUPPLIER]
FeatureMerger
    ATTR_ACCUM_MODE = Merge Supplier
    ATTR_CONFLICT_RES_LOOKUP = REQUESTOR_IF_CONFLICT
    IGNORE_NULLS = No
    JOIN_KEYS = @Value(gml_id) @Value(gml_id) AUTO
    MERGE_TYPE_VAL = ATTRIBUTES
    PROCESS_DUPS = NO
    REJECT_NULL_MISSING_KEYS = No
    SUPPLIERS_FIRST = No
    ATTR_CONFLICT_RES = Use Requestor
    MERGE_TYPE = Attributes Only
    MERGED -> AttributeManager
    UNMERGED_REQUESTOR -> AttributeManager
AttributeManager
    ATTR_TABLE = SET_TO ALKIS (buffer) = FME_CONDITIONAL:DEFAULT_VALUE'1010'BOOL_OP;OR;COMPOSITE_TEST;1;TEST @Value(function) = bijeenkomstfunctie'3030'BOOL_OP;OR;COMPOSITE_TEST;1;TEST @Value(function) = bijeenkomstfunctie,gezondheidszorgfunctie,industriefunctie,kantoorfunctie,logiesfunctie,overige gebruiksfunctie,winkelfunctie,woonfunctie'1110'BOOL_OP;OR;COMPOSITE_TEST;1;TEST @Value(function) = bijeenkomstfunctie,gezondheidszorgfunctie,industriefunctie,overige gebruiksfunctie,woonfunctie'1110'BOOL_OP;OR;COMPOSITE_TEST;1;TEST @Value(function) = bijeenkomstfunctie,gezondheidszorgfunctie,kantoorfunctie,winkelfunctie,woonfunctie'1110'BOOL_OP;OR;COMPOSITE_TEST;1;TEST @Value(function) = bijeenkomstfunctie,gezondheidszorgfunctie,kantoorfunctie,woonfunctie'1110'BOOL_OP;OR;COMPOSITE_TEST;1;TEST @Value(function) = bijeenkomstfunctie,gezondheidszorgfunctie,onderwijsfunctie,sportfunctie,woonfunctie'1110'BOOL_OP;OR;COMPOSITE_TEST;1;TEST @Value(function) = bijeenkomstfunctie,gezondheidszorgfunctie,overige gebruiksfunctie,woonfunctie'1110'BOOL_OP;OR;COMPOSITE_TEST;1;TEST @Value(function) = bijeenkomstfunctie,gezondheidszorgfunctie,winkelfunctie,woonfunctie'1110'BOOL_OP;OR;COMPOSITE_TEST;1;TEST @Value(function) = bijeenkomstfunctie,gezondheidszorgfunctie,woonfunctie'3050'BOOL_OP;OR;COMPOSITE_TEST;1;TEST @Value(function) = bijeenkomstfunctie,industriefunctie'2200'BOOL_OP;OR;COMPOSITE_TEST;1;TEST @Value(function) = bijeenkomstfunctie,industriefunctie,kantoorfunctie,logiesfunctie,onderwijsfunctie,overige gebruiksfunctie,sportfunctie,woonfunctie'2320'BOOL_OP;OR;COMPOSITE_TEST;1;TEST @Value(function) = bijeenkomstfunctie,industriefunctie,kantoorfunctie,onderwijsfunctie,overige gebruiksfunctie,winkelfunctie'2200'BOOL_OP;OR;COMPOSITE_TEST;1;TEST @Value(function) = bijeenkomstfunctie,industriefunctie,kantoorfunctie,overige gebruiksfunctie'2200'BOOL_OP;OR;COMPOSITE_TEST;1;TEST @Value(function) = bijeenkomstfunctie,industriefunctie,kantoorfunctie,overige gebruiksfunctie,winkelfunctie,woonfunctie'2320'BOOL_OP;OR;COMPOSITE_TEST;1;TEST @Value(function) = bijeenkomstfunctie,industriefunctie,kantoorfunctie,overige gebruiksfunctie,woonfunctie'2320'BOOL_OP;OR;COMPOSITE_TEST;1;TEST @Value(function) = bijeenkomstfunctie,industriefunctie,kantoorfunctie,winkelfunctie,woonfunctie'2320'BOOL_OP;OR;COMPOSITE_TEST;1;TEST @Value(function) = bijeenkomstfunctie,industriefunctie,onderwijsfunctie'2320'BOOL_OP;OR;COMPOSITE_TEST;1;TEST @Value(function) = bijeenkomstfunctie,industriefunctie,onderwijsfunctie,overige gebruiksfunctie'2320'BOOL_OP;OR;COMPOSITE_TEST;1;TEST @Value(function) = bijeenkomstfunctie,industriefunctie,onderwijsfunctie,woonfunctie'2320'BOOL_OP;OR;COMPOSITE_TEST;1;TEST @Value(function) = bijeenkomstfunctie,industriefunctie,overige gebruiksfunctie,sportfunctie,woonfunctie'2320'BOOL_OP;OR;COMPOSITE_TEST;1;TEST @Value(function) = bijeenkomstfunctie,industriefunctie,overige gebruiksfunctie,winkelfunctie'2200'BOOL_OP;OR;COMPOSITE_TEST;1;TEST @Value(function) = bijeenkomstfunctie,industriefunctie,overige gebruiksfunctie,woonfunctie'2320'BOOL_OP;OR;COMPOSITE_TEST;1;TEST @Value(function) = bijeenkomstfunctie,industriefunctie,winkelfunctie,woonfunctie'2320'BOOL_OP;OR;COMPOSITE_TEST;1;TEST @Value(function) = bijeenkomstfunctie,industriefunctie,woonfunctie'2320'BOOL_OP;OR;COMPOSITE_TEST;1;TEST @Value(function) = bijeenkomstfunctie,kantoorfunctie,overige gebruiksfunctie'2200'BOOL_OP;OR;COMPOSITE_TEST;1;TEST @Value(function) = bijeenkomstfunctie,kantoorfunctie,overige gebruiksfunctie,sportfunctie,winkelfunctie,woonfunctie'2320'BOOL_OP;OR;COMPOSITE_TEST;1;TEST @Value(function) = bijeenkomstfunctie,kantoorfunctie,overige gebruiksfunctie,winkelfunctie,woonfunctie'2320'BOOL_OP;OR;COMPOSITE_TEST;1;TEST @Value(function) = bijeenkomstfunctie,logiesfunctie'2070'BOOL_OP;OR;COMPOSITE_TEST;1;TEST @Value(function) = bijeenkomstfunctie,logiesfunctie,winkelfunctie,woonfunctie'2070'BOOL_OP;OR;COMPOSITE_TEST;1;TEST @Value(function) = bijeenkomstfunctie,onderwijsfunctie'3020'BOOL_OP;OR;COMPOSITE_TEST;1;TEST @Value(function) = bijeenkomstfunctie,onderwijsfunctie,overige gebruiksfunctie'3020'BOOL_OP;OR;COMPOSITE_TEST;1;TEST @Value(function) = bijeenkomstfunctie,onderwijsfunctie,sportfunctie'3020'BOOL_OP;OR;COMPOSITE_TEST;1;TEST @Value(function) = bijeenkomstfunctie,onderwijsfunctie,woonfunctie'1110'BOOL_OP;OR;COMPOSITE_TEST;1;TEST @Value(function) = bijeenkomstfunctie,overige gebruiksfunctie,sportfunctie,woonfunctie'1110'BOOL_OP;OR;COMPOSITE_TEST;1;TEST @Value(function) = bijeenkomstfunctie,overige gebruiksfunctie,winkelfunctie,woonfunctie'1110'BOOL_OP;OR;COMPOSITE_TEST;1;TEST @Value(function) = bijeenkomstfunctie,overige gebruiksfunctie,woonfunctie'1110'BOOL_OP;OR;COMPOSITE_TEST;1;TEST @Value(function) = bijeenkomstfunctie,sportfunctie'3210'BOOL_OP;OR;COMPOSITE_TEST;1;TEST @Value(function) = bijeenkomstfunctie,winkelfunctie'2000'BOOL_OP;OR;COMPOSITE_TEST;1;TEST @Value(function) = bijeenkomstfunctie,winkelfunctie,woonfunctie'2310'BOOL_OP;OR;COMPOSITE_TEST;1;TEST @Value(function) = bijeenkomstfunctie,woonfunctie'1110'BOOL_OP;OR;COMPOSITE_TEST;1;TEST @Value(function) = gezondheidszorgfunctie'3050'BOOL_OP;OR;COMPOSITE_TEST;1;TEST @Value(function) = gezondheidszorgfunctie,industriefunctie,kantoorfunctie,overige gebruiksfunctie,winkelfunctie,woonfunctie'2310'BOOL_OP;OR;COMPOSITE_TEST;1;TEST @Value(function) = gezondheidszorgfunctie,industriefunctie,onderwijsfunctie,overige gebruiksfunctie'2010'BOOL_OP;OR;COMPOSITE_TEST;1;TEST @Value(function) = gezondheidszorgfunctie,industriefunctie,onderwijsfunctie,overige gebruiksfunctie,winkelfunctie,woonfunctie'2310'BOOL_OP;OR;COMPOSITE_TEST;1;TEST @Value(function) = gezondheidszorgfunctie,industriefunctie,overige gebruiksfunctie,woonfunctie'2310'BOOL_OP;OR;COMPOSITE_TEST;1;TEST @Value(function) = gezondheidszorgfunctie,industriefunctie,woonfunctie'2310'BOOL_OP;OR;COMPOSITE_TEST;1;TEST @Value(function) = gezondheidszorgfunctie,kantoorfunctie,logiesfunctie'2310'BOOL_OP;OR;COMPOSITE_TEST;1;TEST @Value(function) = gezondheidszorgfunctie,kantoorfunctie,overige gebruiksfunctie,woonfunctie'2310'BOOL_OP;OR;COMPOSITE_TEST;1;TEST @Value(function) = gezondheidszorgfunctie,kantoorfunctie,winkelfunctie'2000'BOOL_OP;OR;COMPOSITE_TEST;1;TEST @Value(function) = gezondheidszorgfunctie,kantoorfunctie,woonfunctie'2310'BOOL_OP;OR;COMPOSITE_TEST;1;TEST @Value(function) = gezondheidszorgfunctie,logiesfunctie'2000'BOOL_OP;OR;COMPOSITE_TEST;1;TEST @Value(function) = gezondheidszorgfunctie,onderwijsfunctie,sportfunctie'2010'BOOL_OP;OR;COMPOSITE_TEST;1;TEST @Value(function) = gezondheidszorgfunctie,onderwijsfunctie,winkelfunctie,woonfunctie'1120'BOOL_OP;OR;COMPOSITE_TEST;1;TEST @Value(function) = gezondheidszorgfunctie,onderwijsfunctie,woonfunctie'1120'BOOL_OP;OR;COMPOSITE_TEST;1;TEST @Value(function) = gezondheidszorgfunctie,overige gebruiksfunctie'1120'BOOL_OP;OR;COMPOSITE_TEST;1;TEST @Value(function) = gezondheidszorgfunctie,overige gebruiksfunctie,winkelfunctie,woonfunctie'1120'BOOL_OP;OR;COMPOSITE_TEST;1;TEST @Value(function) = gezondheidszorgfunctie,overige gebruiksfunctie,woonfunctie'3050'BOOL_OP;OR;COMPOSITE_TEST;1;TEST @Value(function) = gezondheidszorgfunctie,woonfunctie'3050'BOOL_OP;OR;COMPOSITE_TEST;1;TEST @Value(function) = industriefunctie'2110'BOOL_OP;OR;COMPOSITE_TEST;1;TEST @Value(function) = industriefunctie,kantoorfunctie,overige gebruiksfunctie'2200'BOOL_OP;OR;COMPOSITE_TEST;1;TEST @Value(function) = industriefunctie,kantoorfunctie,overige gebruiksfunctie,sportfunctie,winkelfunctie,woonfunctie'2320'BOOL_OP;OR;COMPOSITE_TEST;1;TEST @Value(function) = industriefunctie,kantoorfunctie,overige gebruiksfunctie,winkelfunctie,woonfunctie'2320'BOOL_OP;OR;COMPOSITE_TEST;1;TEST @Value(function) = industriefunctie,kantoorfunctie,overige gebruiksfunctie,woonfunctie'2320'BOOL_OP;OR;COMPOSITE_TEST;1;TEST @Value(function) = industriefunctie,kantoorfunctie,winkelfunctie,woonfunctie'2320'BOOL_OP;OR;COMPOSITE_TEST;1;TEST @Value(function) = industriefunctie,kantoorfunctie,woonfunctie'2320'BOOL_OP;OR;COMPOSITE_TEST;1;TEST @Value(function) = industriefunctie,logiesfunctie'2070'BOOL_OP;OR;COMPOSITE_TEST;1;TEST @Value(function) = industriefunctie,logiesfunctie,winkelfunctie,woonfunctie'2070'BOOL_OP;OR;COMPOSITE_TEST;1;TEST @Value(function) = industriefunctie,logiesfunctie,woonfunctie'2070'BOOL_OP;OR;COMPOSITE_TEST;1;TEST @Value(function) = industriefunctie,onderwijsfunctie,overige gebruiksfunctie,woonfunctie'2320'BOOL_OP;OR;COMPOSITE_TEST;1;TEST @Value(function) = industriefunctie,onderwijsfunctie,woonfunctie'2320'BOOL_OP;OR;COMPOSITE_TEST;1;TEST @Value(function) = industriefunctie,overige gebruiksfunctie'2200'BOOL_OP;OR;COMPOSITE_TEST;1;TEST @Value(function) = industriefunctie,overige gebruiksfunctie,sportfunctie,woonfunctie'1110'BOOL_OP;OR;COMPOSITE_TEST;1;TEST @Value(function) = industriefunctie,overige gebruiksfunctie,winkelfunctie,woonfunctie'2320'BOOL_OP;OR;COMPOSITE_TEST;1;TEST @Value(function) = industriefunctie,overige gebruiksfunctie,woonfunctie'2320'BOOL_OP;OR;COMPOSITE_TEST;1;TEST @Value(function) = industriefunctie,winkelfunctie'2200'BOOL_OP;OR;COMPOSITE_TEST;1;TEST @Value(function) = industriefunctie,winkelfunctie,woonfunctie'2320'BOOL_OP;OR;COMPOSITE_TEST;1;TEST @Value(function) = industriefunctie,woonfunctie'2320'BOOL_OP;OR;COMPOSITE_TEST;1;TEST @Value(function) = kantoorfunctie'2020'BOOL_OP;OR;COMPOSITE_TEST;1;TEST @Value(function) = kantoorfunctie,onderwijsfunctie'3020'BOOL_OP;OR;COMPOSITE_TEST;1;TEST @Value(function) = kantoorfunctie,overige gebruiksfunctie'2000'BOOL_OP;OR;COMPOSITE_TEST;1;TEST @Value(function) = kantoorfunctie,overige gebruiksfunctie,winkelfunctie,woonfunctie'2000'BOOL_OP;OR;COMPOSITE_TEST;1;TEST @Value(function) = kantoorfunctie,winkelfunctie,woonfunctie'2000'BOOL_OP;OR;COMPOSITE_TEST;1;TEST @Value(function) = kantoorfunctie,woonfunctie'2000'BOOL_OP;OR;COMPOSITE_TEST;1;TEST @Value(function) = logiesfunctie'2070'BOOL_OP;OR;COMPOSITE_TEST;1;TEST @Value(function) = logiesfunctie,winkelfunctie'2070'BOOL_OP;OR;COMPOSITE_TEST;1;TEST @Value(function) = logiesfunctie,winkelfunctie,woonfunctie'2070'BOOL_OP;OR;COMPOSITE_TEST;1;TEST @Value(function) = logiesfunctie,woonfunctie'2070'BOOL_OP;OR;COMPOSITE_TEST;1;TEST @Value(function) = onderwijsfunctie'3020'BOOL_OP;OR;COMPOSITE_TEST;1;TEST @Value(function) = onderwijsfunctie,overige gebruiksfunctie'3020'BOOL_OP;OR;COMPOSITE_TEST;1;TEST @Value(function) = onderwijsfunctie,overige gebruiksfunctie,sportfunctie'3020'BOOL_OP;OR;COMPOSITE_TEST;1;TEST @Value(function) = onderwijsfunctie,overige gebruiksfunctie,woonfunctie'1120'BOOL_OP;OR;COMPOSITE_TEST;1;TEST @Value(function) = onderwijsfunctie,sportfunctie'3020'BOOL_OP;OR;COMPOSITE_TEST;1;TEST @Value(function) = onderwijsfunctie,winkelfunctie,woonfunctie'1120'BOOL_OP;OR;COMPOSITE_TEST;1;TEST @Value(function) = onderwijsfunctie,woonfunctie'1120'BOOL_OP;OR;COMPOSITE_TEST;1;TEST @Value(function) = overige gebruiksfunctie'3000'BOOL_OP;OR;COMPOSITE_TEST;1;TEST @Value(function) = overige gebruiksfunctie,winkelfunctie,woonfunctie'1110'BOOL_OP;OR;COMPOSITE_TEST;1;TEST @Value(function) = overige gebruiksfunctie,woonfunctie'1110'BOOL_OP;OR;COMPOSITE_TEST;1;TEST @Value(function) = sportfunctie'3210'BOOL_OP;OR;COMPOSITE_TEST;1;TEST @Value(function) = sportfunctie,woonfunctie'1120'BOOL_OP;OR;COMPOSITE_TEST;1;TEST @Value(function) = tuinhuisje'1313'BOOL_OP;OR;COMPOSITE_TEST;1;TEST @Value(function) = winkelfunctie'2050'BOOL_OP;OR;COMPOSITE_TEST;1;TEST @Value(function) = winkelfunctie,woonfunctie'2000'BOOL_OP;OR;COMPOSITE_TEST;1;TEST @Value(function) = woonfunctie'1010'FME_NUM_CONDITIONS104___
    -> Reprojector
Reprojector
    DEST = EPSG:28992
    INTERPOLATION_TYPE = ,NearestNeighbor
    RASTER_CELL_SIZE_LOOKUP = ,PreserveCells
    RASTER_TOLERANCE = 0.0
    INTERPOLATION_TYPE_NAME = Nearest Neighbor
    RASTER_CELL_SIZE = Preserve Cells
    REPROJECTED -> Building (writer CITYGML_3)
Address (reader CITYGML_2)
    attributes: citygml_target_uri xml_buffer, citygml_feature_role xml_buffer, citygml_feature_role_attr_name xml_buffer, citygml_feature_role_attr_val xml_buffer, gml_description xml_buffer, gml_name xml_buffer, citygml_address xml_xml, type xml_buffer
    -> Reprojector_2
Reprojector_2
    DEST = EPSG:28992
    INTERPOLATION_TYPE = ,NearestNeighbor
    RASTER_CELL_SIZE_LOOKUP = ,PreserveCells
    RASTER_TOLERANCE = 0.0
    INTERPOLATION_TYPE_NAME = Nearest Neighbor
    RASTER_CELL_SIZE = Preserve Cells
    REPROJECTED -> Address (writer CITYGML_3)
Address (writer CITYGML_3)
    attributes: citygml_target_uri xml_buffer, citygml_feature_role xml_buffer, citygml_feature_role_attr_name xml_buffer, citygml_feature_role_attr_val xml_buffer, gml_description xml_buffer, gml_name xml_buffer, citygml_address xml_xml, type xml_buffer
Appearance (reader CITYGML_2)
    attributes: citygml_target_uri xml_buffer, citygml_feature_role xml_buffer, citygml_feature_role_attr_name xml_buffer, citygml_feature_role_attr_val xml_buffer, gml_description xml_buffer, gml_name xml_buffer, citygml_surface_data_member{}.xlink_href xml_buffer, type xml_buffer
    -> Reprojector_3
Reprojector_3
    DEST = EPSG:28992
    INTERPOLATION_TYPE = ,NearestNeighbor
    RASTER_CELL_SIZE_LOOKUP = ,PreserveCells
    RASTER_TOLERANCE = 0.0
    INTERPOLATION_TYPE_NAME = Nearest Neighbor
    RASTER_CELL_SIZE = Preserve Cells
    REPROJECTED -> Appearance (writer CITYGML_3)
Appearance (writer CITYGML_3)
    attributes: citygml_target_uri xml_buffer, citygml_feature_role xml_buffer, citygml_feature_role_attr_name xml_buffer, citygml_feature_role_attr_val xml_buffer, gml_description xml_buffer, gml_name xml_buffer, citygml_surface_data_member{}.xlink_href xml_buffer, type xml_buffer
BuildingInstallation (reader CITYGML_2)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_class xml_buffer, citygml_class_codeSpace xml_buffer, citygml_function{} xml_buffer, citygml_function{}.codeSpace xml_buffer, citygml_usage{} xml_buffer, citygml_usage{}.codeSpace xml_buffer, citygml_level_of_detail{} xml_buffer, citygml_bounded_by{}.xlink_href xml_buffer, type xml_buffer
    -> Reprojector_4
Reprojector_4
    DEST = EPSG:28992
    INTERPOLATION_TYPE = ,NearestNeighbor
    RASTER_CELL_SIZE_LOOKUP = ,PreserveCells
    RASTER_TOLERANCE = 0.0
    INTERPOLATION_TYPE_NAME = Nearest Neighbor
    RASTER_CELL_SIZE = Preserve Cells
    REPROJECTED -> BuildingInstallation (writer CITYGML_3)
BuildingInstallation (writer CITYGML_3)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_class xml_buffer, citygml_class_codeSpace xml_buffer, citygml_function{} xml_buffer, citygml_function{}.codeSpace xml_buffer, citygml_usage{} xml_buffer, citygml_usage{}.codeSpace xml_buffer, citygml_level_of_detail{} xml_buffer, citygml_bounded_by{}.xlink_href xml_buffer, type xml_buffer
BuildingPart (reader CITYGML_2)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_class xml_buffer, citygml_class_codeSpace xml_buffer, citygml_function{} xml_buffer, citygml_function{}.codeSpace xml_buffer, citygml_usage{} xml_buffer, citygml_usage{}.codeSpace xml_buffer, citygml_year_of_construction xml_buffer, citygml_year_of_demolition xml_buffer, citygml_roof_type xml_buffer, citygml_roof_type_codeSpace xml_buffer, citygml_measured_height xml_real64, citygml_measured_height_units xml_buffer, citygml_storeys_above_ground xml_uint64, citygml_storeys_below_ground xml_uint64, citygml_storey_heights_above_ground xml_buffer,
      citygml_storey_heights_above_ground_units xml_buffer, citygml_storey_heights_below_ground xml_buffer, citygml_storey_heights_below_ground_units xml_buffer, citygml_outer_building_installation{}.xlink_href xml_buffer, citygml_interior_building_installation{}.xlink_href xml_buffer, citygml_bounded_by{}.xlink_href xml_buffer, citygml_level_of_detail{} xml_buffer, citygml_interior_room{}.xlink_href xml_buffer, citygml_consists_of_building_part{}.xlink_href xml_buffer, citygml_address{}.xlink_href xml_buffer, type xml_buffer
    -> Reprojector_5
Reprojector_5
    DEST = EPSG:28992
    INTERPOLATION_TYPE = ,NearestNeighbor
    RASTER_CELL_SIZE_LOOKUP = ,PreserveCells
    RASTER_TOLERANCE = 0.0
    INTERPOLATION_TYPE_NAME = Nearest Neighbor
    RASTER_CELL_SIZE = Preserve Cells
    REPROJECTED -> BuildingPart (writer CITYGML_3)
BuildingPart (writer CITYGML_3)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_class xml_buffer, citygml_class_codeSpace xml_buffer, citygml_function{} xml_buffer, citygml_function{}.codeSpace xml_buffer, citygml_usage{} xml_buffer, citygml_usage{}.codeSpace xml_buffer, citygml_year_of_construction xml_buffer, citygml_year_of_demolition xml_buffer, citygml_roof_type xml_buffer, citygml_roof_type_codeSpace xml_buffer, citygml_measured_height xml_real64, citygml_measured_height_units xml_buffer, citygml_storeys_above_ground xml_uint64, citygml_storeys_below_ground xml_uint64, citygml_storey_heights_above_ground xml_buffer,
      citygml_storey_heights_above_ground_units xml_buffer, citygml_storey_heights_below_ground xml_buffer, citygml_storey_heights_below_ground_units xml_buffer, citygml_outer_building_installation{}.xlink_href xml_buffer, citygml_interior_building_installation{}.xlink_href xml_buffer, citygml_bounded_by{}.xlink_href xml_buffer, citygml_level_of_detail{} xml_buffer, citygml_interior_room{}.xlink_href xml_buffer, citygml_consists_of_building_part{}.xlink_href xml_buffer, citygml_address{}.xlink_href xml_buffer, type xml_buffer
CityModel (reader CITYGML_2)
    attributes: citygml_target_uri xml_buffer, gml_description xml_buffer, gml_name xml_buffer, citygml_city_object_member{}.xlink_href xml_buffer, citygml_appearance_member{}.xlink_href xml_buffer, gml_feature_member{}.xlink_href xml_buffer, type xml_buffer
    -> Reprojector_6
Reprojector_6
    DEST = EPSG:28992
    INTERPOLATION_TYPE = ,NearestNeighbor
    RASTER_CELL_SIZE_LOOKUP = ,PreserveCells
    RASTER_TOLERANCE = 0.0
    INTERPOLATION_TYPE_NAME = Nearest Neighbor
    RASTER_CELL_SIZE = Preserve Cells
    REPROJECTED -> CityModel (writer CITYGML_3)
CityModel (writer CITYGML_3)
    attributes: citygml_target_uri xml_buffer, gml_description xml_buffer, gml_name xml_buffer, citygml_city_object_member{}.xlink_href xml_buffer, citygml_appearance_member{}.xlink_href xml_buffer, gml_feature_member{}.xlink_href xml_buffer, type xml_buffer
ClosureSurface (reader CITYGML_2)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_level_of_detail{} xml_buffer, citygml_opening{}.xlink_href xml_buffer, type xml_buffer
    -> Reprojector_7
Reprojector_7
    DEST = EPSG:28992
    INTERPOLATION_TYPE = ,NearestNeighbor
    RASTER_CELL_SIZE_LOOKUP = ,PreserveCells
    RASTER_TOLERANCE = 0.0
    INTERPOLATION_TYPE_NAME = Nearest Neighbor
    RASTER_CELL_SIZE = Preserve Cells
    REPROJECTED -> ClosureSurface (writer CITYGML_3)
ClosureSurface (writer CITYGML_3)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_level_of_detail{} xml_buffer, citygml_opening{}.xlink_href xml_buffer, type xml_buffer
GroundSurface (reader CITYGML_2)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_level_of_detail{} xml_buffer, citygml_opening{}.xlink_href xml_buffer, type xml_buffer
    -> Reprojector_9
Reprojector_9
    DEST = EPSG:28992
    INTERPOLATION_TYPE = ,NearestNeighbor
    RASTER_CELL_SIZE_LOOKUP = ,PreserveCells
    RASTER_TOLERANCE = 0.0
    INTERPOLATION_TYPE_NAME = Nearest Neighbor
    RASTER_CELL_SIZE = Preserve Cells
    REPROJECTED -> GroundSurface (writer CITYGML_3)
GroundSurface (writer CITYGML_3)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_level_of_detail{} xml_buffer, citygml_opening{}.xlink_href xml_buffer, type xml_buffer
OuterCeilingSurface (reader CITYGML_2)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_level_of_detail{} xml_buffer, citygml_opening{}.xlink_href xml_buffer, type xml_buffer
    -> Reprojector_10
Reprojector_10
    DEST = EPSG:28992
    INTERPOLATION_TYPE = ,NearestNeighbor
    RASTER_CELL_SIZE_LOOKUP = ,PreserveCells
    RASTER_TOLERANCE = 0.0
    INTERPOLATION_TYPE_NAME = Nearest Neighbor
    RASTER_CELL_SIZE = Preserve Cells
    REPROJECTED -> OuterCeilingSurface (writer CITYGML_3)
OuterCeilingSurface (writer CITYGML_3)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_level_of_detail{} xml_buffer, citygml_opening{}.xlink_href xml_buffer, type xml_buffer
Building (reader CITYGML_4)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_class xml_buffer, citygml_class_codeSpace xml_buffer, citygml_function{} xml_buffer, citygml_function{}.codeSpace xml_buffer, citygml_usage{} xml_buffer, citygml_usage{}.codeSpace xml_buffer, citygml_year_of_construction xml_buffer, citygml_year_of_demolition xml_buffer, citygml_roof_type xml_buffer, citygml_roof_type_codeSpace xml_buffer, citygml_measured_height xml_real64, citygml_measured_height_units xml_buffer, citygml_storeys_above_ground xml_uint64, citygml_storeys_below_ground xml_uint64, citygml_storey_heights_above_ground xml_buffer,
      citygml_storey_heights_above_ground_units xml_buffer, citygml_storey_heights_below_ground xml_buffer, citygml_storey_heights_below_ground_units xml_buffer, citygml_outer_building_installation{}.xlink_href xml_buffer, citygml_interior_building_installation{}.xlink_href xml_buffer, citygml_bounded_by{}.xlink_href xml_buffer, citygml_level_of_detail{} xml_buffer, citygml_interior_room{}.xlink_href xml_buffer, citygml_consists_of_building_part{}.xlink_href xml_buffer, citygml_address{}.xlink_href xml_buffer, buildingColour xml_buffer, numberResidents xml_buffer
    -> AttributeManager_2
AttributeManager_2
    ATTR_TABLE = SET_TO ALKIS (buffer) = 1010
    -> Building (writer CITYGML_3)
Building (writer CITYGML_3)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_class xml_buffer, citygml_class_codeSpace xml_buffer, citygml_function{} xml_buffer, citygml_function{}.codeSpace xml_buffer, citygml_usage{} xml_buffer, citygml_usage{}.codeSpace xml_buffer, citygml_year_of_construction xml_buffer, citygml_year_of_demolition xml_buffer, citygml_roof_type xml_buffer, citygml_roof_type_codeSpace xml_buffer, citygml_measured_height xml_real64, citygml_measured_height_units xml_buffer, citygml_storeys_above_ground xml_uint64, citygml_storeys_below_ground xml_uint64, citygml_storey_heights_above_ground xml_buffer,
      citygml_storey_heights_above_ground_units xml_buffer, citygml_storey_heights_below_ground xml_buffer, citygml_storey_heights_below_ground_units xml_buffer, citygml_outer_building_installation{}.xlink_href xml_buffer, citygml_interior_building_installation{}.xlink_href xml_buffer, citygml_bounded_by{}.xlink_href xml_buffer, citygml_level_of_detail{} xml_buffer, citygml_interior_room{}.xlink_href xml_buffer, citygml_consists_of_building_part{}.xlink_href xml_buffer, citygml_address{}.xlink_href xml_buffer, AANTAL_ADRESSEN xml_buffer, AANTAL_BOUWLAGEN xml_buffer, BEGINGELDIGHEID xml_buffer, BUURT xml_buffer, GEBOUWNUMMER xml_buffer, HOOGSTE_BOUWLAAG xml_buffer, LAAGSTE_BOUWLAAG xml_buffer, PANDSOORT xml_buffer, WIJK xml_buffer, type xml_buffer, citygml_function{0} xml_buffer
