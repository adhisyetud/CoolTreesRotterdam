FME workspace 7_future_tree_sqltree.fmw

Parameters:
- SourceDataset_SPATIALITE_NATIVE = C:\MSc\Q2_2\Cooling_Rotterdam\Start_3\03_Intermediate_Results\01_Todays_Trees_Per_Buurt\Round\00_All_Feijenoord_Round.sqlite   # SpatiaLite Database
- SourceDataset_SPATIALITE_NATIVE_9 = C:\MSc\Q2_2\Cooling_Rotterdam\Start_3\03_Intermediate_Results\2Buurt\CT\S\Round_CT_Afr_Summer.sqlite   # SpatiaLite Database
- DestDataset_CSV2 = C:\MSc\Q2_2\Cooling_Rotterdam\Start_3\03_Intermediate_Results\2Buurt\FT   # Destination CSV (Comma Separated Value) Folder
- SourceDataset_SPATIALITE_NATIVE_7 = C:\MSc\Q2_2\Cooling_Rotterdam\Start_3\03_Intermediate_Results\2Buurt\CT\S\Round_CT_Kvz_Summer.sqlite   # SpatiaLite Database
- SourceDataset_SPATIALITE_NATIVE_6 = C:\MSc\Q2_2\Cooling_Rotterdam\Start_3\03_Intermediate_Results\2Buurt\CT\W\Round_CT_Afr_Winter.sqlite   # SpatiaLite Database
- SourceDataset_SPATIALITE_NATIVE_8 = C:\MSc\Q2_2\Cooling_Rotterdam\Start_3\03_Intermediate_Results\2Buurt\CT\W\Round_CT_Kvz_Winter.sqlite   # SpatiaLite Database
- DestDataset_SPATIALITE_NATIVE_2 = C:\MSc\Q2_2\Cooling_Rotterdam\Start_3\03_Intermediate_Results\2Buurt\FT\S\Round_FT_Kvz_Summer.sqlite   # SpatiaLite Database
- DestDataset_SPATIALITE_NATIVE_3 = C:\MSc\Q2_2\Cooling_Rotterdam\Start_3\03_Intermediate_Results\2Buurt\FT\W\Round_FT_Kvz_Winter.sqlite   # SpatiaLite Database
- DestDataset_SPATIALITE_NATIVE_4 = C:\MSc\Q2_2\Cooling_Rotterdam\Start_3\03_Intermediate_Results\2Buurt\FT\W\Round_FT_Afr_Winter.sqlite   # SpatiaLite Database
- DestDataset_SPATIALITE_NATIVE = C:\MSc\Q2_2\Cooling_Rotterdam\Start_3\03_Intermediate_Results\2Buurt\FT\S\Round_FT_Afr_Summer.sqlite   # SpatiaLite Database

Readers:
- SPATIALITE_NATIVE_1: SPATIALITE_NATIVE from $(SourceDataset_SPATIALITE_NATIVE)
- SPATIALITE_NATIVE_2: SPATIALITE_NATIVE from $(SourceDataset_SPATIALITE_NATIVE_9)
- SPATIALITE_NATIVE_3: SPATIALITE_NATIVE from $(SourceDataset_SPATIALITE_NATIVE_7)
- SPATIALITE_NATIVE_4: SPATIALITE_NATIVE from $(SourceDataset_SPATIALITE_NATIVE_6)
- SPATIALITE_NATIVE_5: SPATIALITE_NATIVE from $(SourceDataset_SPATIALITE_NATIVE_8)

Writers:
- CSV2_1: CSV2 to $(DestDataset_CSV2)
- SPATIALITE_NATIVE_6: SPATIALITE_NATIVE to $(DestDataset_SPATIALITE_NATIVE)
- SPATIALITE_NATIVE_7: SPATIALITE_NATIVE to $(DestDataset_SPATIALITE_NATIVE_2)
- SPATIALITE_NATIVE_8: SPATIALITE_NATIVE to $(DestDataset_SPATIALITE_NATIVE_3)
- SPATIALITE_NATIVE_9: SPATIALITE_NATIVE to $(DestDataset_SPATIALITE_NATIVE_4)

merged (reader SPATIALITE_NATIVE_1)
    attributes: ogc_fid integer, rowid integer, gml_id text, gml_parent_id text, citygml_target_uri text, citygml_feature_role text, citygml_feature_role_attr_name text, citygml_feature_role_attr_val text, gml_description text, gml_name text, citygml_creationdate text, citygml_terminationdate text, externalreference{}.externalobject.name text, externalreference{}.externalobject.uri text, externalreference{}.informationsystem text, citygml_generalizes_to{}.xlink_href text, citygml_relative_to_terrain text, citygml_relative_to_water text, citygml_class text, citygml_class_codespace text, citygml_function{} text, citygml_function{}.codespace text, citygml_usage{} text, citygml_usage{}.codespace text, citygml_species text, citygml_species_codespace text, citygml_height float, citygml_height_units text, citygml_trunk_diameter float, citygml_trunk_diameter_units text,
      citygml_crown_diameter float, citygml_crown_diameter_units text, citygml_level_of_detail{} text, aanlegjaar text, beheerobjectomschrijving text, boom_id text, boomsortiment text, boomsortiment_nederlands text, boomstatus text, brondatum text, buurt text, geslacht text, hoogte text, laatste_mutatie text, ontwikkeling text, stamdiameter text, stamlengte text, straat text, thema text, wijk text, tree_part text, _clipped text, type text, _elevation float, _offset_roof text, layer text, path text
    -> AttributeCreator
AttributeCreator
    ATTR_TABLE:
      SET_TO 0_last_update (real64) = @Left(@Value(laatste_mutatie),4)
      SET_TO 0_planting_year (real64) = @Value(aanlegjaar)
      SET_TO 0_2050_age (varchar(200)) = @sub(2050,@Value(0_planting_year))
      SET_TO 0_age_real (varchar(200)) = @sub(@Value(0_last_update),@Value(0_planting_year))
      SET_TO 0_crown_growth_rate_peryear (varchar(200)) = @round(@div(@Value(citygml_crown_diameter),@Value(0_age_real)),1)
      SET_TO 0_height_growth_rate_peryear (varchar(200)) = @round(@div(@Value(stamlengte),@Value(0_age_real)),1)
    -> TestFilter_3
TestFilter_3
    DEFAULT_VALUE = <UNFILTERED>
    PASSED_TEST_GROUP_OUTPUT = FIRST
    TEST_LIST:
      "BOOL_OP,OR,COMPOSITE_TEST,""""""1"""""",TEST_CLAUSE,TEST @Value(0_age_real) = 0",Type_0,"BOOL_OP,AND,COMPOSITE_TEST,""""""1 AND 2"""""",TEST_CLAUSE,TEST @Value(0_age_real) <= 15
      TEST @Value(0_2050_age) < 40",Type_1,"BOOL_OP,AND,COMPOSITE_TEST,""""""1"""""",TEST_CLAUSE,TEST @sub(40,@Value(0_age_real)) > 1",Type_2
    Type_0 -> No_Growth
    Type_1 -> Fast_Growth
    Type_2 -> Middle_Growth
    <UNFILTERED> -> No_Growth
Fast_Growth: AttributeCreator
    ATTR_TABLE:
      SET_TO 0_add_diameter (real64) = @mult((@sub(@Value(0_2050_age),@Value(0_age_real))),@Value(0_crown_growth_rate_peryear))
      SET_TO 0_add_height (varchar(200)) = @mult((@sub(@Value(0_2050_age),@Value(0_age_real))),@Value(0_height_growth_rate_peryear))
    -> NullAttributeMapper
Middle_Growth: AttributeCreator
    ATTR_TABLE = SET_TO 0_add_diameter (real64) = @mult((@sub(40,@Value(0_age_real))),@Value(0_height_growth_rate_peryear),0.5)
    -> NullAttributeMapper
No_Growth: AttributeCreator
    ATTR_TABLE = SET_TO 0_add_diameter (uint8) = 0
    -> NullAttributeMapper
NullAttributeMapper
    ATTRCHOICE_ACTION = SELECTED
    ATTRLIST = 0_add_diameter 0_add_height
    NEW_VALUE = 0
    NULL_TREATMENT_LU = SETVALUE
    SOURCE_ATTR_VAL_LU = SETNULL EMPTY MISSINGATTR
    ATTRCHOICE = Selected Attributes
    NULL_TREATMENT = New Value
    SOURCE_ATTR_VAL = Null Empty "Missing (Selected Attributes Only)"
    -> AttributeManager
AttributeManager
    ATTR_TABLE = SET_TO 0_add_diameter (real64) = @round(@Value(0_add_diameter),1)
    -> AttributeManager_2
AttributeManager_2
    ATTR_TABLE = SET_TO citygml_crown_diameter (real64) = @add(@Value(0_add_diameter),@Value(citygml_crown_diameter))
    -> DuplicateFilter
DuplicateFilter
    INPUT_ORDERED_CHOICE_LOOKUP = NO
    KEYATTR = gml_id
    INPUT_ORDERED_CHOICE = No
    UNIQUE -> TestFilter
TestFilter
    DEFAULT_VALUE = <UNFILTERED>
    PASSED_TEST_GROUP_OUTPUT = FIRST
    TEST_LIST = "BOOL_OP,OR,COMPOSITE_TEST,""""""1"""""",TEST_CLAUSE,TEST @Value(0_add_height) = 0",0,"BOOL_OP,OR,COMPOSITE_TEST,""""""1"""""",TEST_CLAUSE,TEST @Value(0_add_height) >= 2",2
    0 -> AttributeManager_4
    2 -> AttributeManager_3
AttributeManager_4
    ATTR_TABLE = SET_TO 0_add_height (uint8) = 0
    -> TestFilter_7
AttributeManager_3
    ATTR_TABLE = SET_TO 0_add_height (real32) = 2.5
    -> TestFilter_7
TestFilter_7
    DEFAULT_VALUE = <UNFILTERED>
    PASSED_TEST_GROUP_OUTPUT = FIRST
    TEST_LIST = "BOOL_OP,OR,COMPOSITE_TEST,""""""1"""""",TEST_CLAUSE,TEST @Value(0_add_diameter) = 0",0,"BOOL_OP,OR,COMPOSITE_TEST,""""""1"""""",TEST_CLAUSE,TEST @Value(0_add_diameter) >= 2",2
    0 -> AttributeManager_5
    2 -> AttributeManager_6
    <UNFILTERED> -> AttributeManager_7
AttributeManager_5
    ATTR_TABLE = SET_TO 0_add_diameter (real64) = 0
    -> AttributeKeeper
AttributeManager_6
    ATTR_TABLE = SET_TO 0_add_diameter (real64) = 2
    -> AttributeKeeper
AttributeManager_7
    ATTR_TABLE = SET_TO 0_add_diameter (real64) = @round(@Value(0_add_diameter),1)
    -> AttributeKeeper
AttributeKeeper
    CREATE_BULK_MODE_FEATURES = NO
    KEEP_ATTRS = gml_id,0_add_diameter,0_add_height
    -> GeometryRemover
GeometryRemover
    REMOVE_COORDSYS = No
    -> Tree_growth (writer CSV2_1)
    -> FeatureJoiner [RIGHT]
    -> FeatureJoiner_2 [RIGHT]
    -> FeatureJoiner_3 [RIGHT]
    -> FeatureJoiner_4 [RIGHT]
Tree_growth (writer CSV2_1)
    attributes: 0_add_diameter real64, gml_id string, 0_add_height real32
Table1 (reader SPATIALITE_NATIVE_2)
    attributes: gml_id text, gml_parent_id text, citygml_target_uri text, citygml_feature_role text, citygml_feature_role_attr_name text, citygml_feature_role_attr_val text, gml_description text, gml_name text, citygml_creationDate text, citygml_terminationDate text, externalReference{}.externalObject.name text, externalReference{}.externalObject.uri text, externalReference{}.informationSystem text, citygml_generalizes_to{}.xlink_href text, citygml_relative_to_terrain varchar(33), citygml_relative_to_water varchar(38), citygml_class text, citygml_class_codeSpace text, citygml_function{} text, citygml_function{}.codeSpace text, citygml_usage{} text, citygml_usage{}.codeSpace text, citygml_species text, citygml_species_codeSpace text, citygml_height double, citygml_height_units text, citygml_trunk_diameter double, citygml_trunk_diameter_units text, citygml_crown_diameter double, citygml_crown_diameter_units text,
      citygml_level_of_detail{} text, Aanlegjaar text, Beheerobjectomschrijving text, Boom_id text, Boomsortiment text, Boomsortiment_nederlands text, Boomstatus text, Brondatum text, Buurt text, Geslacht text, Hoogte text, Laatste_mutatie text, Ontwikkeling text, Stamdiameter text, Stamlengte text, Straat text, Thema text, Wijk text, tree_part text, _clipped varchar(3), Type text, _xmin double, _xmax double, _ymin double, _ymax double, _zmin double, _zmax double
    -> FeatureJoiner [LEFT]
FeatureJoiner
    ATTR_CONFLICT_RES_LOOKUP = USE_LEFT
    GEOMETRY_HANDLING_LOOKUP = USE_LEFT
    JOIN_KEYS = gml_id gml_id AUTO
    JOIN_MODE = Inner
    ATTR_CONFLICT_RES = Prefer Left
    GEOMETRY_HANDLING = Prefer Left
    JOINED -> TestFilter_2
TestFilter_2
    DEFAULT_VALUE = <UNFILTERED>
    PASSED_TEST_GROUP_OUTPUT = FIRST
    TEST_LIST:
      "BOOL_OP,OR,COMPOSITE_TEST,""""""1 OR 2"""""",TEST_CLAUSE,TEST @Value(0_add_diameter) = 0
      TEST @Value(0_add_height) = 0",0
    0 -> AttributeManager_8
    <UNFILTERED> -> Bufferer
Bufferer
    ANGLE = 30
    CAP_STYLE_LOOKUP = CAP_ARC
    CORNER_STYLE_LOOKUP = JOIN_ARC
    MODE = AREA
    OFFSET = @Value(0_add_diameter)/2
    OFFSET_UNITS = METERS
    PRECISION = APPROX
    CAP_STYLE = Arc
    CORNER_STYLE = Arc
    BUFFERED -> AttributeManager_8
AttributeManager_8
    ATTR_TABLE:
      SET_TO citygml_crown_diameter (real64) = @add(@Value(citygml_crown_diameter),@Value(0_add_diameter))
      SET_TO _zmax (real64) = @add(@Value(_zmax),@Value(0_add_height))
      REMOVE 0_add_diameter (real64)
      REMOVE 0_add_height (uint8)
    -> 3DForcer
3DForcer
    KEEPZVAL = No
    ZVALATTR = @Value(_zmin)
    -> Table1 (writer SPATIALITE_NATIVE_6)
Table1 (writer SPATIALITE_NATIVE_6)
    attributes: gml_id text, gml_parent_id text, citygml_target_uri text, citygml_feature_role text, citygml_feature_role_attr_name text, citygml_feature_role_attr_val text, gml_description text, gml_name text, citygml_creationDate text, citygml_terminationDate text, externalReference{}.externalObject.name text, externalReference{}.externalObject.uri text, externalReference{}.informationSystem text, citygml_generalizes_to{}.xlink_href text, citygml_relative_to_terrain varchar(33), citygml_relative_to_water varchar(38), citygml_class text, citygml_class_codeSpace text, citygml_function{} text, citygml_function{}.codeSpace text, citygml_usage{} text, citygml_usage{}.codeSpace text, citygml_species text, citygml_species_codeSpace text, citygml_height double, citygml_height_units text, citygml_trunk_diameter double, citygml_trunk_diameter_units text, citygml_crown_diameter double, citygml_crown_diameter_units text,
      citygml_level_of_detail{} text, Aanlegjaar text, Beheerobjectomschrijving text, Boom_id text, Boomsortiment text, Boomsortiment_nederlands text, Boomstatus text, Brondatum text, Buurt text, Geslacht text, Hoogte text, Laatste_mutatie text, Ontwikkeling text, Stamdiameter text, Stamlengte text, Straat text, Thema text, Wijk text, tree_part text, _clipped varchar(3), Type text, _xmin double, _xmax double, _ymin double, _ymax double, _zmin double, _zmax double
Table1 (reader SPATIALITE_NATIVE_3)
    attributes: gml_id text, gml_parent_id text, citygml_target_uri text, citygml_feature_role text, citygml_feature_role_attr_name text, citygml_feature_role_attr_val text, gml_description text, gml_name text, citygml_creationDate text, citygml_terminationDate text, externalReference{}.externalObject.name text, externalReference{}.externalObject.uri text, externalReference{}.informationSystem text, citygml_generalizes_to{}.xlink_href text, citygml_relative_to_terrain varchar(33), citygml_relative_to_water varchar(38), citygml_class text, citygml_class_codeSpace text, citygml_function{} text, citygml_function{}.codeSpace text, citygml_usage{} text, citygml_usage{}.codeSpace text, citygml_species text, citygml_species_codeSpace text, citygml_height double, citygml_height_units text, citygml_trunk_diameter double, citygml_trunk_diameter_units text, citygml_crown_diameter double, citygml_crown_diameter_units text,
      citygml_level_of_detail{} text, Aanlegjaar text, Beheerobjectomschrijving text, Boom_id text, Boomsortiment text, Boomsortiment_nederlands text, Boomstatus text, Brondatum text, Buurt text, Geslacht text, Hoogte text, Laatste_mutatie text, Ontwikkeling text, Stamdiameter text, Stamlengte text, Straat text, Thema text, Wijk text, tree_part text, _clipped varchar(3), Type text, _xmin double, _xmax double, _ymin double, _ymax double, _zmin double, _zmax double
    -> FeatureJoiner_2 [LEFT]
FeatureJoiner_2
    ATTR_CONFLICT_RES_LOOKUP = USE_LEFT
    GEOMETRY_HANDLING_LOOKUP = USE_LEFT
    JOIN_KEYS = gml_id gml_id AUTO
    JOIN_MODE = Inner
    ATTR_CONFLICT_RES = Prefer Left
    GEOMETRY_HANDLING = Prefer Left
    JOINED -> TestFilter_4
TestFilter_4
    DEFAULT_VALUE = <UNFILTERED>
    PASSED_TEST_GROUP_OUTPUT = FIRST
    TEST_LIST:
      "BOOL_OP,OR,COMPOSITE_TEST,""""""1 OR 2"""""",TEST_CLAUSE,TEST @Value(0_add_diameter) = 0
      TEST @Value(0_add_height) = 0",0
    0 -> AttributeManager_9
    <UNFILTERED> -> Bufferer_2
Bufferer_2
    ANGLE = 30
    CAP_STYLE_LOOKUP = CAP_ARC
    CORNER_STYLE_LOOKUP = JOIN_ARC
    MODE = AREA
    OFFSET = @Value(0_add_diameter)/2
    OFFSET_UNITS = METERS
    PRECISION = APPROX
    CAP_STYLE = Arc
    CORNER_STYLE = Arc
    BUFFERED -> AttributeManager_9
AttributeManager_9
    ATTR_TABLE:
      SET_TO citygml_crown_diameter (real64) = @add(@Value(citygml_crown_diameter),@Value(0_add_diameter))
      SET_TO _zmax (real64) = @add(@Value(_zmax),@Value(0_add_height))
      REMOVE 0_add_diameter (real64)
      REMOVE 0_add_height (uint8)
    -> 3DForcer_2
3DForcer_2
    KEEPZVAL = No
    ZVALATTR = @Value(_zmin)
    -> Table1 (writer SPATIALITE_NATIVE_7)
Table1 (writer SPATIALITE_NATIVE_7)
    attributes: gml_id text, gml_parent_id text, citygml_target_uri text, citygml_feature_role text, citygml_feature_role_attr_name text, citygml_feature_role_attr_val text, gml_description text, gml_name text, citygml_creationDate text, citygml_terminationDate text, externalReference{}.externalObject.name text, externalReference{}.externalObject.uri text, externalReference{}.informationSystem text, citygml_generalizes_to{}.xlink_href text, citygml_relative_to_terrain varchar(33), citygml_relative_to_water varchar(38), citygml_class text, citygml_class_codeSpace text, citygml_function{} text, citygml_function{}.codeSpace text, citygml_usage{} text, citygml_usage{}.codeSpace text, citygml_species text, citygml_species_codeSpace text, citygml_height double, citygml_height_units text, citygml_trunk_diameter double, citygml_trunk_diameter_units text, citygml_crown_diameter double, citygml_crown_diameter_units text,
      citygml_level_of_detail{} text, Aanlegjaar text, Beheerobjectomschrijving text, Boom_id text, Boomsortiment text, Boomsortiment_nederlands text, Boomstatus text, Brondatum text, Buurt text, Geslacht text, Hoogte text, Laatste_mutatie text, Ontwikkeling text, Stamdiameter text, Stamlengte text, Straat text, Thema text, Wijk text, tree_part text, _clipped varchar(3), Type text, _xmin double, _xmax double, _ymin double, _ymax double, _zmin double, _zmax double
Table1 (reader SPATIALITE_NATIVE_4)
    attributes: gml_id text, gml_parent_id text, citygml_target_uri text, citygml_feature_role text, citygml_feature_role_attr_name text, citygml_feature_role_attr_val text, gml_description text, gml_name text, citygml_creationDate text, citygml_terminationDate text, externalReference{}.externalObject.name text, externalReference{}.externalObject.uri text, externalReference{}.informationSystem text, citygml_generalizes_to{}.xlink_href text, citygml_relative_to_terrain varchar(33), citygml_relative_to_water varchar(38), citygml_class text, citygml_class_codeSpace text, citygml_function{} text, citygml_function{}.codeSpace text, citygml_usage{} text, citygml_usage{}.codeSpace text, citygml_species text, citygml_species_codeSpace text, citygml_height double, citygml_height_units text, citygml_trunk_diameter double, citygml_trunk_diameter_units text, citygml_crown_diameter double, citygml_crown_diameter_units text,
      citygml_level_of_detail{} text, Aanlegjaar text, Beheerobjectomschrijving text, Boom_id text, Boomsortiment text, Boomsortiment_nederlands text, Boomstatus text, Brondatum text, Buurt text, Geslacht text, Hoogte text, Laatste_mutatie text, Ontwikkeling text, Stamdiameter text, Stamlengte text, Straat text, Thema text, Wijk text, tree_part text, _clipped varchar(3), Type text, _xmin double, _xmax double, _ymin double, _ymax double, _zmin double, _zmax double
    -> FeatureJoiner_3 [LEFT]
FeatureJoiner_3
    ATTR_CONFLICT_RES_LOOKUP = USE_LEFT
    GEOMETRY_HANDLING_LOOKUP = USE_LEFT
    JOIN_KEYS = gml_id gml_id AUTO
    JOIN_MODE = Inner
    ATTR_CONFLICT_RES = Prefer Left
    GEOMETRY_HANDLING = Prefer Left
    JOINED -> TestFilter_5
TestFilter_5
    DEFAULT_VALUE = <UNFILTERED>
    PASSED_TEST_GROUP_OUTPUT = FIRST
    TEST_LIST:
      "BOOL_OP,OR,COMPOSITE_TEST,""""""1 OR 2"""""",TEST_CLAUSE,TEST @Value(0_add_diameter) = 0
      TEST @Value(0_add_height) = 0",0
    0 -> AttributeManager_10
    <UNFILTERED> -> Bufferer_3
Bufferer_3
    ANGLE = 30
    CAP_STYLE_LOOKUP = CAP_ARC
    CORNER_STYLE_LOOKUP = JOIN_ARC
    MODE = AREA
    OFFSET = @Value(0_add_diameter)/2
    OFFSET_UNITS = METERS
    PRECISION = APPROX
    CAP_STYLE = Arc
    CORNER_STYLE = Arc
    BUFFERED -> AttributeManager_10
AttributeManager_10
    ATTR_TABLE:
      SET_TO citygml_crown_diameter (real64) = @add(@Value(citygml_crown_diameter),@Value(0_add_diameter))
      SET_TO _zmax (real64) = @add(@Value(_zmax),@Value(0_add_height))
      REMOVE 0_add_diameter (real64)
      REMOVE 0_add_height (uint8)
    -> 3DForcer_3
3DForcer_3
    KEEPZVAL = No
    ZVALATTR = @Value(_zmin)
    -> Table1 (writer SPATIALITE_NATIVE_9)
Table1 (writer SPATIALITE_NATIVE_9)
    attributes: gml_id text, gml_parent_id text, citygml_target_uri text, citygml_feature_role text, citygml_feature_role_attr_name text, citygml_feature_role_attr_val text, gml_description text, gml_name text, citygml_creationDate text, citygml_terminationDate text, externalReference{}.externalObject.name text, externalReference{}.externalObject.uri text, externalReference{}.informationSystem text, citygml_generalizes_to{}.xlink_href text, citygml_relative_to_terrain varchar(33), citygml_relative_to_water varchar(38), citygml_class text, citygml_class_codeSpace text, citygml_function{} text, citygml_function{}.codeSpace text, citygml_usage{} text, citygml_usage{}.codeSpace text, citygml_species text, citygml_species_codeSpace text, citygml_height double, citygml_height_units text, citygml_trunk_diameter double, citygml_trunk_diameter_units text, citygml_crown_diameter double, citygml_crown_diameter_units text,
      citygml_level_of_detail{} text, Aanlegjaar text, Beheerobjectomschrijving text, Boom_id text, Boomsortiment text, Boomsortiment_nederlands text, Boomstatus text, Brondatum text, Buurt text, Geslacht text, Hoogte text, Laatste_mutatie text, Ontwikkeling text, Stamdiameter text, Stamlengte text, Straat text, Thema text, Wijk text, tree_part text, _clipped varchar(3), Type text, _xmin double, _xmax double, _ymin double, _ymax double, _zmin double, _zmax double
Table1 (reader SPATIALITE_NATIVE_5)
    attributes: gml_id text, gml_parent_id text, citygml_target_uri text, citygml_feature_role text, citygml_feature_role_attr_name text, citygml_feature_role_attr_val text, gml_description text, gml_name text, citygml_creationDate text, citygml_terminationDate text, externalReference{}.externalObject.name text, externalReference{}.externalObject.uri text, externalReference{}.informationSystem text, citygml_generalizes_to{}.xlink_href text, citygml_relative_to_terrain varchar(33), citygml_relative_to_water varchar(38), citygml_class text, citygml_class_codeSpace text, citygml_function{} text, citygml_function{}.codeSpace text, citygml_usage{} text, citygml_usage{}.codeSpace text, citygml_species text, citygml_species_codeSpace text, citygml_height double, citygml_height_units text, citygml_trunk_diameter double, citygml_trunk_diameter_units text, citygml_crown_diameter double, citygml_crown_diameter_units text,
      citygml_level_of_detail{} text, Aanlegjaar text, Beheerobjectomschrijving text, Boom_id text, Boomsortiment text, Boomsortiment_nederlands text, Boomstatus text, Brondatum text, Buurt text, Geslacht text, Hoogte text, Laatste_mutatie text, Ontwikkeling text, Stamdiameter text, Stamlengte text, Straat text, Thema text, Wijk text, tree_part text, _clipped varchar(3), Type text, _xmin double, _xmax double, _ymin double, _ymax double, _zmin double, _zmax double
    -> FeatureJoiner_4 [LEFT]
FeatureJoiner_4
    ATTR_CONFLICT_RES_LOOKUP = USE_LEFT
    GEOMETRY_HANDLING_LOOKUP = USE_LEFT
    JOIN_KEYS = gml_id gml_id AUTO
    JOIN_MODE = Inner
    ATTR_CONFLICT_RES = Prefer Left
    GEOMETRY_HANDLING = Prefer Left
    JOINED -> TestFilter_6
TestFilter_6
    DEFAULT_VALUE = <UNFILTERED>
    PASSED_TEST_GROUP_OUTPUT = FIRST
    TEST_LIST:
      "BOOL_OP,OR,COMPOSITE_TEST,""""""1 OR 2"""""",TEST_CLAUSE,TEST @Value(0_add_diameter) = 0
      TEST @Value(0_add_height) = 0",0
    0 -> AttributeManager_11
    <UNFILTERED> -> Bufferer_4
Bufferer_4
    ANGLE = 30
    CAP_STYLE_LOOKUP = CAP_ARC
    CORNER_STYLE_LOOKUP = JOIN_ARC
    MODE = AREA
    OFFSET = @Value(0_add_diameter)/2
    OFFSET_UNITS = METERS
    PRECISION = APPROX
    CAP_STYLE = Arc
    CORNER_STYLE = Arc
    BUFFERED -> AttributeManager_11
AttributeManager_11
    ATTR_TABLE:
      SET_TO citygml_crown_diameter (real64) = @add(@Value(citygml_crown_diameter),@Value(0_add_diameter))
      SET_TO _zmax (real64) = @add(@Value(_zmax),@Value(0_add_height))
      REMOVE 0_add_diameter (real64)
      REMOVE 0_add_height (uint8)
    -> 3DForcer_4
3DForcer_4
    KEEPZVAL = No
    ZVALATTR = @Value(_zmin)
    -> Table1 (writer SPATIALITE_NATIVE_8)
Table1 (writer SPATIALITE_NATIVE_8)
    attributes: gml_id text, gml_parent_id text, citygml_target_uri text, citygml_feature_role text, citygml_feature_role_attr_name text, citygml_feature_role_attr_val text, gml_description text, gml_name text, citygml_creationDate text, citygml_terminationDate text, externalReference{}.externalObject.name text, externalReference{}.externalObject.uri text, externalReference{}.informationSystem text, citygml_generalizes_to{}.xlink_href text, citygml_relative_to_terrain varchar(33), citygml_relative_to_water varchar(38), citygml_class text, citygml_class_codeSpace text, citygml_function{} text, citygml_function{}.codeSpace text, citygml_usage{} text, citygml_usage{}.codeSpace text, citygml_species text, citygml_species_codeSpace text, citygml_height double, citygml_height_units text, citygml_trunk_diameter double, citygml_trunk_diameter_units text, citygml_crown_diameter double, citygml_crown_diameter_units text,
      citygml_level_of_detail{} text, Aanlegjaar text, Beheerobjectomschrijving text, Boom_id text, Boomsortiment text, Boomsortiment_nederlands text, Boomstatus text, Brondatum text, Buurt text, Geslacht text, Hoogte text, Laatste_mutatie text, Ontwikkeling text, Stamdiameter text, Stamlengte text, Straat text, Thema text, Wijk text, tree_part text, _clipped varchar(3), Type text, _xmin double, _xmax double, _ymin double, _ymax double, _zmin double, _zmax double
