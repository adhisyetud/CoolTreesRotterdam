FME workspace 11_CSV_Processing_Compare_23_50.fmw

Parameters:
- SourceDataset_CSV2_5 = C:\MSc\Q2_2\Cooling_Rotterdam\Start_3\03_Intermediate_Results\2Buurt\Compare\New_2023_2050\All_Year_2050\Kvz_NoTree_50_10_2050_DIN18599_HEATING_AND_COOLING.csv   # Source CSV (Comma Separated Value) File(s)
- SourceDataset_CITYGML = C:\MSc\Q2_2\Cooling_Rotterdam\Data\Processed\clean_fix_enriched\Kop van Zuid_buildings_cl_fi.gml   # Source CityGML File(s)
- SourceDataset_CSV2_4 = C:\MSc\Q2_2\Cooling_Rotterdam\Start_3\03_Intermediate_Results\2Buurt\Compare\New_2023_2050\All_Year_2023\Kvz_NoTree_50_10_2023_DIN18599_HEATING_AND_COOLING.csv   # Source CSV (Comma Separated Value) File(s)
- DestDataset_SPATIALITE_NATIVE = C:\MSc\Q2_2\Cooling_Rotterdam\Start_3\03_Intermediate_Results\2Buurt\Compare\New_2023_2050\02_Kvz_No_Tree_23_50_Difference_FINAL.sqlite   # SpatiaLite Database

Readers:
- CSV2_2: CSV2 from $(SourceDataset_CSV2_5)
- CITYGML_1: CITYGML from $(SourceDataset_CITYGML)
- CSV2_3: CSV2 from $(SourceDataset_CSV2_4)

Writers:
- SPATIALITE_NATIVE_1: SPATIALITE_NATIVE to $(DestDataset_SPATIALITE_NATIVE)

CSV (reader CSV2_3)
    attributes: GMLId varchar(39), ParentGMLId varchar(20), Latitude varchar(8), Longitude varchar(7), X-coordinate varchar(8), Y-coordinate varchar(9), LOD varchar(5), Year of construction varchar(6), Year of refurbishment varchar(6), Refurbishment Variant varchar(8), ALKIS code varchar(4), PrimaryUsageZoneType varchar(22), PrimaryUsageZoneArea varchar(8), SecondaryUsageZoneType varchar(11), SecondaryUsageZoneArea varchar(6), BuildingType varchar(3), Footprint area varchar(6), Total wall thermal area above ground varchar(7), Total wall thermal area below ground varchar(5), Total outwall area varchar(7), Total shared wall area varchar(6), Total roof area varchar(6), Gross volume varchar(8), Is Gross volume approximated? varchar(5), Heated volume varchar(8), Ridge/mean Height varchar(5), Eaves/mean Height varchar(6), Storey number varchar(3), Average Storey Height varchar(3), Number of households varchar(3),
      Number of occupants varchar(3), Attic Heating varchar(10), Basement Heating varchar(10), Basement ceiling height above ground varchar(3), Surface area to volume ratio varchar(8), Heated area varchar(8), Mean Uvalue varchar(12), Specific domestic hot water demand varchar(14), Domestic hot water demand varchar(9), Specific space heating demand varchar(14), Yearly Heating demand varchar(7), Total Yearly Heating + DHW demand varchar(7), January Heating demand varchar(6), February Heating demand varchar(6), March Heating demand varchar(6), April Heating demand varchar(6), May Heating demand varchar(5), June Heating demand varchar(5), July Heating demand varchar(5), August Heating demand varchar(5), September Heating demand varchar(5), October Heating demand varchar(6), November Heating demand varchar(6), December Heating demand varchar(6), Specific space Cooling demand varchar(14), Yearly Cooling demand varchar(7), January Cooling demand varchar(5), February Cooling demand varchar(5), March Cooling demand varchar(5), April Cooling demand varchar(5),
      May Cooling demand varchar(6), June Cooling demand varchar(6), July Cooling demand varchar(6), August Cooling demand varchar(6), September Cooling demand varchar(6), October Cooling demand varchar(5), November Cooling demand varchar(5), December Cooling demand varchar(5)
    -> AttributeKeeper
AttributeKeeper
    CREATE_BULK_MODE_FEATURES = NO
    KEEP_ATTRS = Footprint area,GMLId,Yearly Cooling demand,Yearly Heating demand
    -> AttributeRenamer
AttributeRenamer
    ATTR_TABLE:
      RENAME_SET_DEFAULT Yearly Cooling demand > Yearly Cooling Demand (kWh/year)_2050
      RENAME_SET_DEFAULT Yearly Heating demand > Yearly Heating Demand (kWh/year)_2050
    KEEP_RENAMED_ONLY = no
    MISSING_INPUT_ATTRS = REMOVE
    -> FeatureMerger_2 [SUPPLIER]
CSV (reader CSV2_2)
    attributes: GMLId varchar(39), ParentGMLId varchar(20), Latitude varchar(8), Longitude varchar(7), X-coordinate varchar(8), Y-coordinate varchar(9), LOD varchar(5), Year of construction varchar(6), Year of refurbishment varchar(6), Refurbishment Variant varchar(8), ALKIS code varchar(4), PrimaryUsageZoneType varchar(22), PrimaryUsageZoneArea varchar(8), SecondaryUsageZoneType varchar(11), SecondaryUsageZoneArea varchar(6), BuildingType varchar(3), Footprint area varchar(6), Total wall thermal area above ground varchar(7), Total wall thermal area below ground varchar(5), Total outwall area varchar(7), Total shared wall area varchar(6), Total roof area varchar(6), Gross volume varchar(8), Is Gross volume approximated? varchar(5), Heated volume varchar(8), Ridge/mean Height varchar(5), Eaves/mean Height varchar(6), Storey number varchar(3), Average Storey Height varchar(3), Number of households varchar(3),
      Number of occupants varchar(3), Attic Heating varchar(10), Basement Heating varchar(10), Basement ceiling height above ground varchar(3), Surface area to volume ratio varchar(8), Heated area varchar(8), Mean Uvalue varchar(12), Specific domestic hot water demand varchar(14), Domestic hot water demand varchar(9), Specific space heating demand varchar(14), Yearly Heating demand varchar(7), Total Yearly Heating + DHW demand varchar(7), January Heating demand varchar(6), February Heating demand varchar(6), March Heating demand varchar(6), April Heating demand varchar(6), May Heating demand varchar(5), June Heating demand varchar(5), July Heating demand varchar(5), August Heating demand varchar(5), September Heating demand varchar(5), October Heating demand varchar(6), November Heating demand varchar(6), December Heating demand varchar(6), Specific space Cooling demand varchar(14), Yearly Cooling demand varchar(7), January Cooling demand varchar(5), February Cooling demand varchar(5), March Cooling demand varchar(5), April Cooling demand varchar(5),
      May Cooling demand varchar(6), June Cooling demand varchar(6), July Cooling demand varchar(6), August Cooling demand varchar(6), September Cooling demand varchar(6), October Cooling demand varchar(5), November Cooling demand varchar(5), December Cooling demand varchar(5)
    -> AttributeKeeper_2
AttributeKeeper_2
    CREATE_BULK_MODE_FEATURES = NO
    KEEP_ATTRS = Footprint area,GMLId,Yearly Cooling demand,Yearly Heating demand
    -> AttributeRenamer_2
AttributeRenamer_2
    ATTR_TABLE:
      RENAME_SET_DEFAULT Yearly Cooling demand > Yearly Cooling Demand (kWh/year)_2023
      RENAME_SET_DEFAULT Yearly Heating demand > Yearly Heating Demand (kWh/year)_2023
    KEEP_RENAMED_ONLY = no
    MISSING_INPUT_ATTRS = REMOVE
    -> FeatureMerger_2 [REQUESTOR]
FeatureMerger_2
    ATTR_ACCUM_MODE = Merge Supplier
    ATTR_CONFLICT_RES_LOOKUP = REQUESTOR_IF_CONFLICT
    IGNORE_NULLS = No
    JOIN_KEYS = @Value(GMLId) @Value(GMLId) AUTO
    MERGE_TYPE_VAL = ATTRIBUTES
    PROCESS_DUPS = NO
    REJECT_NULL_MISSING_KEYS = No
    SUPPLIERS_FIRST = No
    ATTR_CONFLICT_RES = Use Requestor
    MERGE_TYPE = Attributes Only
    MERGED -> AttributeManager
AttributeManager
    ATTR_TABLE:
      SET_TO Yearly Energy Demand (kWh/year)_2023 (real32) = @add(@Value(Yearly Cooling Demand (kWh/year)_2023),@Value(Yearly Heating Demand (kWh/year)_2023))
      SET_TO N_YCD (kWh/m²/year)_2023 (real32) = @div(@Value(Yearly Cooling Demand (kWh/year)_2023),@Value(Footprint area))
      SET_TO N_YHD (kWh/m²/year)_2023 (real32) = @div(@Value(Yearly Heating Demand (kWh/year)_2023),@Value(Footprint area))
      SET_TO N_YED (kWh/m²/year)_2023 (real32) = @div(@Value(Yearly Energy Demand (kWh/year)_2023),@Value(Footprint area))
      SET_TO Yearly Energy Demand (kWh/year)_2050 (real32) = @add(@Value(Yearly Cooling Demand (kWh/year)_2050),@Value(Yearly Heating Demand (kWh/year)_2050))
      SET_TO N_YCD (kWh/m²/year)_2050 (real32) = @div(@Value(Yearly Cooling Demand (kWh/year)_2050),@Value(Footprint area))
      SET_TO N_YHD (kWh/m²/year)_2050 (real32) = @div(@Value(Yearly Heating Demand (kWh/year)_2050),@Value(Footprint area))
      SET_TO N_YED (kWh/m²/year)_2050 (real32) = @div(@Value(Yearly Energy Demand (kWh/year)_2050),@Value(Footprint area))
    USER_EXPOSED_ATTRIBUTES = ycd_diff,yhd_diff
    -> AttributeManager_3
AttributeManager_3
    ATTR_TABLE:
      SET_TO Diff_N_YED (kWh/m²/year) (real32) = @sub(@Value(N_YED (kWh/m²/year)_2050),@Value(N_YED (kWh/m²/year)_2023))
      SET_TO Diff_N_YCD (kWh/m²/year) (real32) = @sub(@Value(N_YCD (kWh/m²/year)_2050),@Value(N_YCD (kWh/m²/year)_2023))
      SET_TO Diff_N_YHD (kWh/m²/year) (real32) = @sub(@Value(N_YHD (kWh/m²/year)_2050),@Value(N_YHD (kWh/m²/year)_2023))
      SET_TO Diff_YED (real32) = @sub(@Value(Yearly Energy Demand (kWh/year)_2050),@Value(Yearly Energy Demand (kWh/year)_2023))
      SET_TO Diff_YCD (real32) = @sub(@Value(Yearly Cooling Demand (kWh/year)_2050),@Value(Yearly Cooling Demand (kWh/year)_2023))
      SET_TO Diff_YHD (real32) = @sub(@Value(Yearly Heating Demand (kWh/year)_2050),@Value(Yearly Heating Demand (kWh/year)_2023))
    -> AttributeManager_2
AttributeManager_2
    USER_EXPOSED_ATTRIBUTES = ycd_diff,yhd_diff,diff
    -> FeatureMerger [SUPPLIER]
Address (reader CITYGML_1)
    attributes: citygml_target_uri xml_buffer, citygml_feature_role xml_buffer, citygml_feature_role_attr_name xml_buffer, citygml_feature_role_attr_val xml_buffer, gml_description xml_buffer, gml_name xml_buffer, citygml_address xml_xml
Building (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_class xml_buffer, citygml_class_codeSpace xml_buffer, citygml_function{} xml_buffer, citygml_function{}.codeSpace xml_buffer, citygml_usage{} xml_buffer, citygml_usage{}.codeSpace xml_buffer, citygml_year_of_construction xml_buffer, citygml_year_of_demolition xml_buffer, citygml_roof_type xml_buffer, citygml_roof_type_codeSpace xml_buffer, citygml_measured_height xml_real64, citygml_measured_height_units xml_buffer, citygml_storeys_above_ground xml_uint64, citygml_storeys_below_ground xml_uint64, citygml_storey_heights_above_ground xml_buffer,
      citygml_storey_heights_above_ground_units xml_buffer, citygml_storey_heights_below_ground xml_buffer, citygml_storey_heights_below_ground_units xml_buffer, citygml_outer_building_installation{}.xlink_href xml_buffer, citygml_interior_building_installation{}.xlink_href xml_buffer, citygml_bounded_by{}.xlink_href xml_buffer, citygml_level_of_detail{} xml_buffer, citygml_interior_room{}.xlink_href xml_buffer, citygml_consists_of_building_part{}.xlink_href xml_buffer, citygml_address{}.xlink_href xml_buffer, AANTAL_ADRESSEN xml_buffer, AANTAL_BOUWLAGEN xml_buffer, BUURT xml_buffer, HOOGSTE_BOUWLAAG xml_buffer, LAAGSTE_BOUWLAAG xml_buffer, PANDSOORT xml_buffer, WIJK xml_buffer, type xml_buffer
    -> FeatureMerger [REQUESTOR]
BuildingInstallation (reader CITYGML_1)
    attributes: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
BuildingPart (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_class xml_buffer, citygml_class_codeSpace xml_buffer, citygml_function{} xml_buffer, citygml_function{}.codeSpace xml_buffer, citygml_usage{} xml_buffer, citygml_usage{}.codeSpace xml_buffer, citygml_year_of_construction xml_buffer, citygml_year_of_demolition xml_buffer, citygml_roof_type xml_buffer, citygml_roof_type_codeSpace xml_buffer, citygml_measured_height xml_real64, citygml_measured_height_units xml_buffer, citygml_storeys_above_ground xml_uint64, citygml_storeys_below_ground xml_uint64, citygml_storey_heights_above_ground xml_buffer,
      citygml_storey_heights_above_ground_units xml_buffer, citygml_storey_heights_below_ground xml_buffer, citygml_storey_heights_below_ground_units xml_buffer, citygml_outer_building_installation{}.xlink_href xml_buffer, citygml_interior_building_installation{}.xlink_href xml_buffer, citygml_bounded_by{}.xlink_href xml_buffer, citygml_level_of_detail{} xml_buffer, citygml_interior_room{}.xlink_href xml_buffer, citygml_consists_of_building_part{}.xlink_href xml_buffer, citygml_address{}.xlink_href xml_buffer, type xml_buffer
    -> FeatureMerger [REQUESTOR]
FeatureMerger
    ATTR_ACCUM_MODE = Merge Supplier
    ATTR_CONFLICT_RES_LOOKUP = REQUESTOR_IF_CONFLICT
    IGNORE_NULLS = No
    JOIN_KEYS = @Value(gml_id) @Value(GMLId) AUTO
    MERGE_TYPE_VAL = ATTRIBUTES
    PROCESS_DUPS = NO
    REJECT_NULL_MISSING_KEYS = No
    SUPPLIERS_FIRST = No
    ATTR_CONFLICT_RES = Use Requestor
    MERGE_TYPE = Attributes Only
    MERGED -> SurfaceFootprintReplacer
SurfaceFootprintReplacer
    OFFSET_Z_LOOKUP = 0
    SHADOW_TYPE = OVERHEAD
    OFFSET_Z = 0
    SHADOW_MODE = Overhead Shadow
    FOOTPRINT -> Table1 (writer SPATIALITE_NATIVE_1)
Table1 (writer SPATIALITE_NATIVE_1)
    attributes: gml_id text, gml_parent_id text, citygml_target_uri text, citygml_feature_role text, citygml_feature_role_attr_name text, citygml_feature_role_attr_val text, gml_description text, gml_name text, citygml_creationDate text, citygml_terminationDate text, externalReference{}.externalObject.name text, externalReference{}.externalObject.uri text, externalReference{}.informationSystem text, citygml_generalizes_to{}.xlink_href text, citygml_relative_to_terrain varchar(33), citygml_relative_to_water varchar(38), citygml_appearance{}.xlink_href text, citygml_class text, citygml_class_codeSpace text, citygml_function{} text, citygml_function{}.codeSpace text, citygml_usage{} text, citygml_usage{}.codeSpace text, citygml_year_of_construction text, citygml_year_of_demolition text, citygml_roof_type text, citygml_roof_type_codeSpace text, citygml_measured_height double, citygml_measured_height_units text, citygml_storeys_above_ground varchar(20),
      citygml_storeys_below_ground varchar(20), citygml_storey_heights_above_ground text, citygml_storey_heights_above_ground_units text, citygml_storey_heights_below_ground text, citygml_storey_heights_below_ground_units text, citygml_outer_building_installation{}.xlink_href text, citygml_interior_building_installation{}.xlink_href text, citygml_bounded_by{}.xlink_href text, citygml_level_of_detail{} text, citygml_interior_room{}.xlink_href text, citygml_consists_of_building_part{}.xlink_href text, citygml_address{}.xlink_href text, type text, AANTAL_ADRESSEN text, AANTAL_BOUWLAGEN text, BUURT text, HOOGSTE_BOUWLAAG text, LAAGSTE_BOUWLAAG text, PANDSOORT text, WIJK text, GMLId varchar(39), Footprint area float, Diff_N_YED (kWh/m²/year) float, Diff_N_YCD (kWh/m²/year) float, Diff_N_YHD (kWh/m²/year) float, Diff_YED float, Diff_YCD float, Diff_YHD float, Yearly Cooling Demand (kWh/year)_2023 float, Yearly Heating Demand (kWh/year)_2023 float,
      Yearly Energy Demand (kWh/year)_2023 float, N_YCD (kWh/m²/year)_2023 float, N_YHD (kWh/m²/year)_2023 float, N_YED (kWh/m²/year)_2023 float, Yearly Cooling Demand (kWh/year)_2050 float, Yearly Heating Demand (kWh/year)_2050 float, Yearly Energy Demand (kWh/year)_2050 float, N_YCD (kWh/m²/year)_2050 float, N_YHD (kWh/m²/year)_2050 float, N_YED (kWh/m²/year)_2050 float
CityModel (reader CITYGML_1)
    attributes: citygml_target_uri xml_buffer, gml_description xml_buffer, gml_name xml_buffer, citygml_city_object_member{}.xlink_href xml_buffer, citygml_appearance_member{}.xlink_href xml_buffer, gml_feature_member{}.xlink_href xml_buffer
ClosureSurface (reader CITYGML_1)
    attributes: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
GroundSurface (reader CITYGML_1)
    attributes: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
OuterCeilingSurface (reader CITYGML_1)
    attributes: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
OuterFloorSurface (reader CITYGML_1)
    attributes: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
RoofSurface (reader CITYGML_1)
    attributes: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
WallSurface (reader CITYGML_1)
    attributes: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
